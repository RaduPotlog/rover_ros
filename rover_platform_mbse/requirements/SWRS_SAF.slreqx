# SWRS_SAF
rover_safety Software Requirements Specification (ROVER-A1-ROVER_SAFETY-SWRS-V-001). rover_safety provides behavior-tree driven safety supervision in two nav2::LifecycleNodes that configure and activate themselves. rover_safety_node evaluates the battery (health + temperature) with a pure domain policy and, through the RoverSafety tree, trips the software E-Stop or starts a controlled shutdown of the ROS controller (trip E-Stop, shut down remote hosts, power off), also on request via ~/shutdown. rover_led_safety_node selects LED animations (E-Stop, manual action, ready, error, battery level/charging) and requests them from rover_led. The package is outside the hard E-Stop chain (rover_arch/SAFETY_CHAIN.md). It does not implement a platform state machine today; this SWRS assigns the SYS-SR-010 mode manager, its Low Battery thresholds and the SYS-SR-009 state-to-LED mapping to this package as Proposed requirements.

## SWR-SAF-001: Interface: The rover_safety shall, in rover_safety_node, subscribe battery/battery_status (sensor_... (Functional)
The rover_safety shall, in rover_safety_node, subscribe battery/battery_status (sensor_msgs/BatteryState, KeepLast(1), reliable), hardware_interface/safety_command_echo (rover_msgs/SafetyCommandEcho, KeepLast(1), reliable, volatile), system_status (rover_msgs/SystemStatus, KeepLast(1), reliable) and hardware_interface/driver_state (rover_msgs/RoverDriverState, depth 10), and act as a client of hardware_interface/sw_user_e_stop_set (std_srvs/Trigger).
- Rationale: Only the latest reading matters for the safety decision; QoS must be compatible with the volatile publishers.

## SWR-SAF-002: Safety: The rover_safety shall, in rover_safety_node, classify a battery reading with health WA... (Functional)
The rover_safety shall, in rover_safety_node, classify a battery reading with health WATCHDOG_TIMER_EXPIRE, DEAD or OVERVOLTAGE as verdict TRIP_E_STOP.
- Rationale: A pack that is flat, overcharged or silent must not keep driving.

## SWR-SAF-003: Safety: The rover_safety shall, in rover_safety_node, for a battery reading with health OVERHEA... (Functional)
The rover_safety shall, in rover_safety_node, for a battery reading with health OVERHEAT, return verdict SHUTDOWN above battery.temp.fatal (60.0 degC) and TRIP_E_STOP above battery.temp.critical (50.0 degC), and no action otherwise; a high temperature without OVERHEAT health shall not trigger an action.
- Rationale: Escalating thermal protection of the pack; the temperature is only acted on when the BMS itself flags overheat.

## SWR-SAF-004: Parameter: The rover_safety shall, in rover_safety_node, reject battery.temp.critical and battery.... (Functional)
The rover_safety shall, in rover_safety_node, reject battery.temp.critical and battery.temp.fatal outside [-20.0, 100.0] degC and shall fail construction unless critical < fatal.
- Rationale: An inverted threshold pair would skip the E-Stop stage and go straight to shutdown (or never shut down).

## SWR-SAF-005: Functional: The rover_safety shall, in rover_safety_node, tick the RoverSafety behavior tree at tim... (Functional)
The rover_safety shall, in rover_safety_node, tick the RoverSafety behavior tree at timer_frequency (10.0 Hz), calling hardware_interface/sw_user_e_stop_set when the battery verdict is TRIP_E_STOP and the software E-Stop is not already set, and raising SignalShutdown with the verdict reason when the verdict is SHUTDOWN.
- Rationale: Turns the battery verdict into an action within one tick; the E-Stop is not re-requested while already set.

## SWR-SAF-006: Safety: The rover_safety shall, in rover_safety_node, evaluate and act on the battery verdict a... (Functional)
The rover_safety shall, in rover_safety_node, evaluate and act on the battery verdict as soon as a battery reading and the software E-Stop state are available, independently of whether system_status (CPU temperature) has been received.
- Rationale: Today the safety tree is not ticked until battery_status, cpu_temp (from rover_diag_manager's system_status) and sw_e_stop_state are all on the blackboard, so a missing or late rover_diag_manager silently disables the battery E-Stop and shutdown reactions.

## SWR-SAF-007: Functional: The rover_safety shall, in rover_safety_node, once a shutdown is started (SignalShutdow... (Functional)
The rover_safety shall, in rover_safety_node, once a shutdown is started (SignalShutdown or ~/shutdown), halt the safety tree and tick the RoverShutdown tree at timer_frequency, which trips the software E-Stop (best effort), asks every host in shutdown_hosts_path to shut down (best effort, unreachable hosts skipped), and runs shutdown.command (default: the installed shutdown_ros_controller.sh --no-e-stop with the reason exported) within shutdown.command_timeout (15.0 s).
- Rationale: Controlled power-down of the ROS controller on a fatal battery condition or on request, with the rover stopped first.

## SWR-SAF-008: Interface: The rover_safety shall, in rover_safety_node, provide ~/shutdown (std_srvs/Trigger) whe... (Functional)
The rover_safety shall, in rover_safety_node, provide ~/shutdown (std_srvs/Trigger) when shutdown.service_enabled is true (shipped: true), replying immediately with success only when a new shutdown was started, refusing while one is in progress or has succeeded, and refusing retries for shutdown.retry_backoff (30.0 s) after a failed attempt.
- Rationale: Idempotent, non-blocking shutdown requests; a failed power-off must not be hammered.

## SWR-SAF-009: Diagnostics: The rover_safety shall, in rover_safety_node, publish diagnostics under hardware ID Rov... (Functional)
The rover_safety shall, in rover_safety_node, publish diagnostics under hardware ID 'Rover Safety' with the tasks 'Safety inputs' (ERROR when an input is older than input_timeout = 5.0 s, WARN when one was never received), 'Battery safety verdict' (ERROR for any verdict other than none, STALE before the first reading), 'Safety behavior tree' and 'Shutdown' (ERROR after a failed power-off).
- Rationale: Makes the battery reaction, input freshness and shutdown state observable.

## SWR-SAF-010: Lifecycle: The rover_safety shall run rover_safety_node and rover_led_safety_node as nav2::Lifecyc... (Functional)
The rover_safety shall run rover_safety_node and rover_led_safety_node as nav2::LifecycleNodes that configure and activate themselves when autostart_node is true, and that retry a failed configure every configure_retry_period (5.0 s) until it succeeds.
- Rationale: Tree construction fails while a required service (sw_user_e_stop_set, led/set_animation) is not yet up; the nodes must recover without manual intervention.

## SWR-SAF-011: Build: The rover_safety shall, in rover_safety.launch.py, start rover_led_safety_node always a... (Functional)
The rover_safety shall, in rover_safety.launch.py, start rover_led_safety_node always and rover_safety_node only when use_sim is false.
- Rationale: The battery supervision and the shutdown need the real hardware interface and BMS; LED selection also runs in simulation.

## SWR-SAF-012: Safety: The rover_safety shall, in rover_safety_node, evaluate motor-driver temperature from ha... (Functional)
The rover_safety shall, in rover_safety_node, evaluate motor-driver temperature from hardware_interface/driver_state and trip the software E-Stop above a driver temperature limit of [TBD] degC.
- Rationale: The driver-state subscription exists but its callback is a TODO; driver overheating is currently not supervised by software.

## SWR-SAF-013: Interface: The rover_safety shall, in rover_led_safety_node, subscribe battery/battery_status (dep... (Functional)
The rover_safety shall, in rover_led_safety_node, subscribe battery/battery_status (depth 10), hardware_interface/safety_status (KeepLast(1), reliable, volatile) and joy (sensor_msgs/Joy, depth 10), tick the RoverLedSafety tree at timer_frequency (10.0 Hz) once e_stop_state and battery_status have been received, and request animations via led/set_animation (rover_msgs/SetLedAnimation) only when the selected animation changes.
- Rationale: LED state follows the safety inputs; deduplication avoids flooding rover_led.

## SWR-SAF-014: Functional: The rover_safety shall, in rover_led_safety_node, select the state animation E_STOP whi... (Functional)
The rover_safety shall, in rover_led_safety_node, select the state animation E_STOP while SafetyStatus.hw_e_stop_user_button is true, otherwise MANUAL_ACTION while joy button 4 (dead-man) is held, otherwise READY.
- Rationale: Visible indication that the physical E-Stop is pressed.

## SWR-SAF-015: Functional: The rover_safety shall, in rover_led_safety_node, while discharging, request CRITICAL_B... (Functional)
The rover_safety shall, in rover_led_safety_node, while discharging, request CRITICAL_BATTERY below battery.percent.threshold.critical (0.1), LOW_BATTERY from 0.1 up to battery.percent.threshold.low (0.4) repeated every battery.anim_period.low (30.0 s), and BATTERY_NOMINAL at or above 0.4; while charging or full it shall request CHARGER_INSERTED then CHARGING_BATTERY with the percentage rounded to charging_anim_step (0.05), or BATTERY_CHARGED when that rounds to 1.0.
- Rationale: Battery level indication on the LED panels.

## SWR-SAF-016: Functional: The rover_safety shall, in rover_led_safety_node, request the ERROR animation while the... (Functional)
The rover_safety shall, in rover_led_safety_node, request the ERROR animation while the battery status is UNKNOWN (including the BMS watchdog-expired state) or while charging with health OVERHEAT, and NO_ERROR otherwise.
- Rationale: Visible indication of a lost BMS or a charging over-temperature.

## SWR-SAF-017: Diagnostics: The rover_safety shall, in rover_led_safety_node, publish diagnostics under hardware ID... (Functional)
The rover_safety shall, in rover_led_safety_node, publish diagnostics under hardware ID 'Bumper Led' with the tasks 'LED safety inputs' (battery_status and safety_status graded against input_timeout = 5.0 s; joy reported but not graded) and 'LED safety behavior tree'.
- Rationale: A dead hardware interface or BMS must be visible as stale LED inputs.

## SWR-SAF-018: Functional: The rover_safety shall provide a platform mode manager that maintains exactly one curre... (Functional)
The rover_safety shall provide a platform mode manager that maintains exactly one current system state out of Boot, Idle, Teleoperation, Autonomous, Emergency Stop, Fault and Low Battery, and publishes it on a ROS topic with reliable, transient-local QoS (depth 1) on every change.
- Rationale: SYS-SR-010 requires a defined system state machine; no package implements one (rover_safety only runs the battery tree and three LED state verdicts).

## SWR-SAF-019: Functional: The rover_safety shall, in its platform mode manager, implement these transitions: Boot... (Functional)
The rover_safety shall, in its platform mode manager, implement these transitions: Boot -> Idle once all platform nodes are active and the first fresh SafetyStatus has been received; Idle <-> Teleoperation / Autonomous according to the twist_mux input currently selected (teleop inputs vs nav); any state -> Emergency Stop while any stop condition of SafetyStatus/SafetyCommandEcho is active (HW button, SW button, motor-driver fault, latch); Emergency Stop -> Idle only after the latch has been reset; Boot -> Idle within [TBD per SYS-SR-024] s of power-up.
- Rationale: Every SYS-SR-010 transition must be triggerable and observable; Emergency Stop must be left only by an explicit reset (SYS-SR-008).

## SWR-SAF-020: Safety: The rover_safety shall, in its platform mode manager, enter Low Battery when the batter... (Functional)
The rover_safety shall, in its platform mode manager, enter Low Battery when the battery state of charge falls below [TBD per SYS-SR-017] % and shall perform a safe stop (trip the software E-Stop) when it falls below [TBD per SYS-SR-017] %, with both thresholds as validated parameters.
- Rationale: No software SOC threshold exists today: the battery policy acts only on BMS health flags and temperature, and the 0.4/0.1 LED levels do not change behaviour.

## SWR-SAF-021: Safety: The rover_safety shall, in its platform mode manager, enter Fault when the battery verd... (Functional)
The rover_safety shall, in its platform mode manager, enter Fault when the battery verdict is not none, when a safety input is older than input_timeout (5.0 s), or when SafetyStatus.link_healthy is false, and shall leave Fault only when all these conditions have cleared.
- Rationale: Gives SYS-SR-010's Fault state a concrete, testable entry condition from signals the package already evaluates.

## SWR-SAF-022: Functional: The rover_safety shall, in rover_led_safety_node, display each SYS-SR-010 state with a ... (Functional)
The rover_safety shall, in rover_led_safety_node, display each SYS-SR-010 state with a dedicated rover_msgs/LedAnimation according to a documented state-to-LED mapping - at least Emergency Stop -> E_STOP (for hardware button, software button, motor-driver fault and held latch alike), Idle -> READY, Teleoperation -> MANUAL_ACTION, Autonomous -> AUTONOMOUS_READY/AUTONOMOUS_ACTION, Low Battery -> LOW_BATTERY, Fault -> ERROR - with colour and pattern per [TBD per SYS-SR-009].
- Rationale: SYS-SR-009 requires the LED panels to show the system state; today only the hardware button produces E_STOP and there is no Autonomous, Fault or Low Battery state indication derived from a state machine.
