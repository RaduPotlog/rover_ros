# SWRS_CRSF
rover_crsf_teleop Software Requirements Specification (ROVER-A1-ROVER_CRSF_TELEOP-SWRS-V-001). rover_crsf_teleop provides line-of-sight RC teleoperation over an ExpressLRS/CRSF receiver. The receiver is wired through a USB-UART adapter to the RUTX11 router, whose Serial Utilities (Over IP: UDP client, raw mode, 460800 8N1) forward the raw CRSF bytes as UDP datagrams to 192.168.1.201:10111. A lifecycle component (RoverCrsfTeleopNode) decodes that byte stream as published by rover_udp_driver's UdpReceiverNode (rover_crsf_udp_receiver, accepting datagrams from the router, 192.168.1.1, only; both in one single-threaded container), maps two stick channels to TwistStamped commands on the highest-priority twist_mux input (teleop_elrs_cmd_vel_stamped) at 50 Hz, maps two switch channels onto the hardware interface's software E-Stop set/reset and latch-reset services, applies an RC-link failsafe (zero burst then silence), and offers an E-Stop-interlocked per-channel stick calibration with persistence.

## SWR-CRSF-001: Interface: The rover_crsf_teleop shall subscribe the raw CRSF byte stream as udp_msgs/UdpPacket da... (Functional)
The rover_crsf_teleop shall subscribe the raw CRSF byte stream as udp_msgs/UdpPacket datagrams on udp_topic (rc/raw_udp) with QoS depth 100, reliable, from the moment it is configured, and shall feed each datagram's data to the stream CRSF parser without assuming that datagram boundaries coincide with CRSF frame boundaries.
- Rationale: A dropped byte chunk desynchronises the parser until the next sync byte, so the ROS hop must not drop it; decoding while inactive means link health is known the moment teleop is activated. The router cuts datagrams on its serial timeout, not on CRSF frames, so a frame can span two datagrams.

## SWR-CRSF-002: Functional: The rover_crsf_teleop shall decode CRSF RC_CHANNELS_PACKED (0x16, 16 x 11-bit channels)... (Functional)
The rover_crsf_teleop shall decode CRSF RC_CHANNELS_PACKED (0x16, 16 x 11-bit channels) and LINK_STATISTICS (0x14) frames addressed to the flight controller (0xC8), discard frames with a bad CRC8 or out-of-range length byte, and resynchronise on the next sync byte with a bounded buffer.
- Rationale: Only CRC-valid frames may drive the rover; corrupted input must never be interpreted as stick positions.

## SWR-CRSF-003: Interface: The rover_crsf_teleop shall publish velocity commands as geometry_msgs/TwistStamped wit... (Functional)
The rover_crsf_teleop shall publish velocity commands as geometry_msgs/TwistStamped with header.frame_id base_link on teleop_elrs_cmd_vel_stamped through a lifecycle publisher (depth 10) that is active only while the node is ACTIVE.
- Rationale: This is the cmd_elrs input of rover_twist_mux (priority 110); a lifecycle publisher guarantees an inactive node cannot command motion.

## SWR-CRSF-004: Performance: The rover_crsf_teleop shall run its control loop every 20 ms (50 Hz) while ACTIVE and p... (Functional)
The rover_crsf_teleop shall run its control loop every 20 ms (50 Hz) while ACTIVE and publish one command per tick while the sticks are deflected and the link is healthy.
- Rationale: 50 Hz keeps the cmd_elrs input far inside the 0.5 s twist_mux timeout and the 500 ms command watchdog.

## SWR-CRSF-005: Functional: The rover_crsf_teleop shall map linear_x_channel (3) to linear.x in [-0.95, 0.95] m/s a... (Functional)
The rover_crsf_teleop shall map linear_x_channel (3) to linear.x in [-0.95, 0.95] m/s and angular_z_channel (1, inverted) to angular.z in [-1.5, 1.5] rad/s, clamping raw values to the channel's calibrated range and mapping a stick within channel_deadband (30 counts) of its midpoint to exactly 0.0.
- Rationale: Output limits match the drive controller caps; an exact zero at centre is required by the hardware interface's E-Stop reset invariant and by the zero-burst logic.

## SWR-CRSF-006: Functional: The rover_crsf_teleop shall shape each stick axis as (1 - e) * m + e * m^3 of the norma... (Functional)
The rover_crsf_teleop shall shape each stick axis as (1 - e) * m + e * m^3 of the normalised deflection m, with e = linear_x_expo (0.3) and angular_z_expo (0.5), clamping e to [0, 1] and keeping full deflection at the output limits.
- Rationale: Finer low-speed control, matching the web joystick.

## SWR-CRSF-007: Performance: The rover_crsf_teleop shall scale linear.x and angular.z by the same factor so that |v|... (Functional)
The rover_crsf_teleop shall scale linear.x and angular.z by the same factor so that |v| + |w| * effective_track_width / 2 does not exceed max_wheel_rim_speed (1.7 m/s with effective_track_width 1.0204 m).
- Rationale: Keeps the outer-wheel speed under the URDF wheel limit while preserving the commanded arc.

## SWR-CRSF-008: Parameter: The rover_crsf_teleop shall declare linear_x_out_min/max and angular_z_out_min/max defa... (Functional)
The rover_crsf_teleop shall declare linear_x_out_min/max and angular_z_out_min/max defaults no larger in magnitude than 1.0 m/s and 1.7 rad/s and shall refuse to configure with values beyond those limits.
- Rationale: The declared defaults (+/-2.0 m/s, +/-5.0 rad/s) exceed the system velocity limits, so running without the shipped YAML would command beyond SYS-SR-004; configure validation does not check the limits.

## SWR-CRSF-009: Safety: The rover_crsf_teleop shall, when the commanded velocity becomes zero (stick released, ... (Functional)
The rover_crsf_teleop shall, when the commanded velocity becomes zero (stick released, link lost or teleop inhibited), publish zero commands for zero_burst_duration_ms (300 ms) and then publish nothing until a non-zero command is produced.
- Rationale: A burst rather than a single zero means one lost message cannot leave the last motion command standing; going silent lets twist_mux fall through to the next source.

## SWR-CRSF-010: Safety: The rover_crsf_teleop shall judge the RC link healthy only while an RC channels frame w... (Functional)
The rover_crsf_teleop shall judge the RC link healthy only while an RC channels frame was decoded within channel_timeout_ms (200 ms) and, with require_link_stats true, a LINK_STATISTICS frame was decoded within link_stats_timeout_ms (1000 ms) and uplink link quality has not fallen below link_quality_lost_below (30 %) since it was last at or above link_quality_recovered_at (50 %); the link shall be unhealthy before any input.
- Rationale: Frame freshness alone cannot detect a receiver in failsafe that keeps sending held channel values; link quality with hysteresis can, without flapping.

## SWR-CRSF-011: Safety: The rover_crsf_teleop shall, when the RC link is judged lost while ACTIVE, command zero... (Functional)
The rover_crsf_teleop shall, when the RC link is judged lost while ACTIVE, command zero velocity (SWR-CRSF-009 burst), stop publishing and ignore the switch channels until the link is healthy again, without triggering the E-Stop.
- Rationale: Loss of the RC operator link must stop RC-commanded motion at once; twist_mux then falls through to the next source.

## SWR-CRSF-012: Safety: The rover_crsf_teleop shall, on a change of the e_stop_channel (5) switch position, cal... (Functional)
The rover_crsf_teleop shall, on a change of the e_stop_channel (5) switch position, call hardware_interface/sw_user_e_stop_set (std_srvs/Trigger) when it goes low and hardware_interface/sw_user_e_stop_reset when it goes high, and shall call hardware_interface/sw_e_stop_latch_reset when e_stop_latch_reset_channel (4) goes low, evaluated within one 20 ms control tick of the decoded frame.
- Rationale: Gives the RC operator a software E-Stop and an explicit, deliberate reset action; only changes fire, never a resting position.

## SWR-CRSF-013: Safety: The rover_crsf_teleop shall ignore switch positions for switch_settle_frames (100 ticks... (Functional)
The rover_crsf_teleop shall ignore switch positions for switch_settle_frames (100 ticks = 2 s) after start-up and after a calibration inhibit is released, learning the resting position without firing a service call, and shall classify a raw value below channel_switch_threshold (500) as low.
- Rationale: Prevents a spurious E-Stop set/reset from the switch's resting position or from switches moved during a calibration sweep.

## SWR-CRSF-014: Safety: The rover_crsf_teleop shall keep requesting hardware_interface/sw_user_e_stop_set while... (Functional)
The rover_crsf_teleop shall keep requesting hardware_interface/sw_user_e_stop_set while the e_stop_channel switch is low and the request has not been acknowledged with success (service unavailable, pending or refused), instead of dropping the request.
- Rationale: Today an E-Stop set request is dropped with a warning if the service is not ready and is never retried, because requests fire only on a switch change; an operator's E-Stop could therefore be silently lost.

## SWR-CRSF-015: Lifecycle: The rover_crsf_teleop shall be a managed lifecycle node that validates parameters and s... (Functional)
The rover_crsf_teleop shall be a managed lifecycle node that validates parameters and subscribes its inputs in configure, starts the 20 ms control loop in activate, publishes one zero command before its publisher is deactivated in deactivate and in shutdown, and self-transitions to ACTIVE when autostart is true.
- Rationale: A supervisor can take RC teleop off the command path without killing the process; leaving the command path always ends with a stop.

## SWR-CRSF-016: Build: The rover_crsf_teleop shall, in rover_crsf_teleop.launch.py, load rover_udp_drivers Udp... (Functional)
The rover_crsf_teleop shall, in rover_crsf_teleop.launch.py, load rover_udp_driver's UdpReceiverNode as rover_crsf_udp_receiver (ip udp_bind_ip 192.168.1.201, port udp_port 10111, source_ip udp_source_ip 192.168.1.1, all read from the teleop config; udp_read remapped to rc/raw_udp; autostart) and the teleop node into one single-threaded component container (rover_crsf_container) with intra-process communication, and shall not start the UDP receiver when use_sim is true.
- Rationale: Keeps the ~250 rc/raw_udp datagrams per second off the Zenoh router and preserves the node's single-threaded invariant; there is no receiver in simulation, and the simulation machine does not own 192.168.1.201.

## SWR-CRSF-017: Parameter: The rover_crsf_teleop shall fail the configure transition when a channel role is outsid... (Functional)
The rover_crsf_teleop shall fail the configure transition when a channel role is outside 1-16, two roles share a channel, channel_switch_threshold is outside the 0-2047 wire range, zero_burst_duration_ms is negative, channel_timeout_ms or link_stats_timeout_ms is not positive, or the link-quality thresholds are inconsistent.
- Rationale: A mis-set channel would otherwise drive the E-Stop from a stick or read a stick as full negative deflection.

## SWR-CRSF-018: Safety: The rover_crsf_teleop shall start an RC calibration session only while the node is not ... (Functional)
The rover_crsf_teleop shall start an RC calibration session only while the node is not ACTIVE, the operator confirms the E-Stop, and a fresh (within e_stop_state_timeout_s = 1.0 s, link healthy) hardware_interface/safety_status shows the physical E-Stop pressed AND the latch active AND the motor contactor open; it shall refuse activation during a session, inhibit teleop for its duration, cancel it after the E-Stop is released for e_stop_grace_s (1.0 s) and after calibration_timeout_s (300 s).
- Rationale: The sweep drives the sticks to full throw, so motion must be physically impossible and verified, not assumed.

## SWR-CRSF-019: Interface: The rover_crsf_teleop shall provide the calibration services rc/calibration/start (rove... (Functional)
The rover_crsf_teleop shall provide the calibration services rc/calibration/start (rover_msgs/StartRcCalibration), rc/calibration/sweep, finish and cancel (std_srvs/Trigger) and rc/calibration/apply (rover_msgs/SetRcCalibration), publish rc/calibration/state (rover_msgs/RcCalibrationState, reliable, transient-local, depth 1) at calibration_state_rate_hz (5.0 Hz) during a session and on every change, and persist an applied calibration to calibration_file.
- Rationale: A client joining mid-session must immediately learn that teleop is held off; persisted endpoints describe the transmitter actually in use.

## SWR-CRSF-020: Interface: The rover_crsf_teleop shall, when publish_rc_topics is true, echo decoded frames on rc/... (Functional)
The rover_crsf_teleop shall, when publish_rc_topics is true, echo decoded frames on rc/channels (rover_msgs/RcChannels) and rc/link (rover_msgs/RcLinkStatus) with QoS best-effort, volatile, depth 1, each capped at rc_topics_rate_hz (25 Hz; 0 = uncapped).
- Rationale: Observability for tuning and the Cockpit RC page without pulling ~250 messages/s through the Zenoh router; nothing on the rover consumes them.

## SWR-CRSF-021: Diagnostics: The rover_crsf_teleop shall publish diagnostics under hardware ID RC Receiver with the ... (Functional)
The rover_crsf_teleop shall publish diagnostics under hardware ID 'RC Receiver' with the tasks 'RC link', 'E-Stop requests', 'RC channels rate', 'RC UDP link' and 'RC calibration', reporting at most WARN (never ERROR); 'RC channels rate' shall warn when the decoded frame rate deviates by more than rc_channels_rate_tolerance (0.2) from rc_channels_expected_hz (250.0 Hz), and 'RC UDP link' shall warn before the first datagram and when no datagram has arrived for more than 1000 ms.
- Rationale: RC teleop is optional, so its faults are warnings; separate tasks distinguish a dead datagram stream (router, cable or UDP receiver) from an out-of-range transmitter or a refused E-Stop request.

## SWR-CRSF-022: Safety: The rover_crsf_teleop shall accept RC input only from the configured router address: ro... (Functional)
The rover_crsf_teleop shall accept RC input only from the configured router address: rover_crsf_teleop.launch.py shall pass udp_source_ip from the teleop config to the UDP receiver as source_ip, so that datagrams from any other sender are dropped before they are published on rc/raw_udp, and the shipped configuration shall set udp_source_ip to the RUTX11 address (192.168.1.1). A blank udp_source_ip shall keep the router address; only an explicit empty string shall accept any sender, and then the launch file and the teleop node shall each log a warning.
- Rationale: CRSF frames carry no authentication and the ELRS input is twist_mux priority 110, above every other velocity source. Without the filter any host that can reach 192.168.1.201:10111 (a host on the wired LAN, a client of the 192.168.77 AP) could command motion or send E-Stop reset and latch-reset switch edges. UdpPacket.address is the bound address, not the sender, so the teleop node cannot filter itself.
