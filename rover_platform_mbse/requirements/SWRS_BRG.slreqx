# SWRS_BRG
rover_bringup Software Requirements Specification (ROVER-A1-ROVER_BRINGUP-SWRS-V-001). rover_bringup holds the top-level launch files that start the Rover A1 platform software on real hardware. rover_bringup.launch.py gates start-up on the hardware-configuration flag, checks the OS build version, starts rover_controller (ros2_control) and rover_diag_manager first, and starts battery, LED, safety, localization, CRSF teleop and twist_mux once the controllers are active. rover_web_bridges.launch.py starts foxglove_bridge (with topic/service whitelists), rosbridge and rosapi for the web UIs and ros-mcp. Automatic start at power-up is done by the rover_docker container start script, outside this package boundary; the GPS and lidar drivers belong to the sensor payload (rover_sensors). Simulation uses rover_gazebo instead.

## SWR-BRG-001: Lifecycle: The rover_bringup shall start the platform stack only when the environment variable ROB... (Functional)
The rover_bringup shall start the platform stack only when the environment variable ROBOT_HW_CONFIG_CORRECT is true (default true); otherwise it shall log INCORRECT_HW_CONFIG, start no platform node, and keep the launch process alive unless exit_on_wrong_hw is true.
- Rationale: Prevents driving motors with a mismatched hardware configuration while keeping the container up for diagnosis.

## SWR-BRG-002: Diagnostics: The rover_bringup shall log a warning when SYSTEM_BUILD_VERSION (default v1.0.0) is low... (Functional)
The rover_bringup shall log a warning when SYSTEM_BUILD_VERSION (default v1.0.0) is lower than the minimum OS version v1.0.0, and continue the start-up.
- Rationale: Makes an outdated OS image visible without blocking operation.

## SWR-BRG-003: Functional: The rover_bringup shall start rover_controller (robot description, controller_manager a... (Functional)
The rover_bringup shall start rover_controller (robot description, controller_manager and the ros2_control controllers) with use_sim False as the first stage of the platform stack.
- Rationale: SYS-SR-020 requires ros2_control for the drive hardware interface; the drive must be up before its consumers.

## SWR-BRG-004: Functional: The rover_bringup shall start rover_diag_manager (system diagnostics and the diagnostic... (Functional)
The rover_bringup shall start rover_diag_manager (system diagnostics and the diagnostic aggregator) together with rover_controller in the first stage.
- Rationale: Diagnostics must be available from the start to report failures of later stages (SYS-SR-022).

## SWR-BRG-005: Lifecycle: The rover_bringup shall start rover_battery, rover_led, rover_safety, rover_localizatio... (Functional)
The rover_bringup shall start rover_battery, rover_led, rover_safety, rover_localization, rover_crsf_teleop and rover_twist_mux exactly once, when rover_controller emits the ControllersActive event (after the rover_imu_broadcaster spawner succeeds) or after controllers_ready_timeout seconds (default 20.0) with a warning if the event never arrives.
- Rationale: Consumers of joint states, odometry and IMU must not start before the controllers are active; the timeout covers a hung spawner.

## SWR-BRG-006: Safety: The rover_bringup shall start rover_safety in the second stage unless the launch argume... (Functional)
The rover_bringup shall start rover_safety in the second stage unless the launch argument disable_manager is True (default False).
- Rationale: rover_safety implements the software E-stop handling and state/LED logic (SYS-SR-007, SYS-SR-008, SYS-SR-010).

## SWR-BRG-007: Functional: The rover_bringup shall start rover_localization with use_ekf True and fuse_gps set fro... (Functional)
The rover_bringup shall start rover_localization with use_ekf True and fuse_gps set from the use_gps argument (default $ROVER_SYSTEM_USE_GPS, else false).
- Rationale: The fused odometry is required on hardware; GPS fusion is selected per deployment.

## SWR-BRG-008: Parameter: The rover_bringup shall pass namespace (default $ROVER_SYSTEM_NAMESPACE, else empty), l... (Functional)
The rover_bringup shall pass namespace (default $ROVER_SYSTEM_NAMESPACE, else empty), log_level (DEBUG/INFO/WARN/ERROR/FATAL, default INFO) and common_dir_path (default empty) to every included launch file.
- Rationale: One namespace and log level for the whole platform; per-package config overrides from a common directory.

## SWR-BRG-009: Build: The rover_bringup shall declare run dependencies on rover_controller, rover_localizatio... (Functional)
The rover_bringup shall declare run dependencies on rover_controller, rover_localization, rover_diag_manager, rover_twist_mux, rover_crsf_teleop, rover_battery, rover_utils, rover_safety, rover_led, rover_udp_driver, foxglove_bridge, rosbridge_server and rmw_zenoh_cpp for the hardware build type (ROVER_ROS_BUILD_TYPE == hardware).
- Rationale: rosdep must install everything the hardware launch starts, including the Zenoh RMW.

## SWR-BRG-010: Build: The rover_bringup shall run on the ROS 2 distribution fixed in SYS-SR-020 with rmw_zeno... (Functional)
The rover_bringup shall run on the ROS 2 distribution fixed in SYS-SR-020 with rmw_zenoh_cpp as the RMW implementation.
- Rationale: SYS-SR-020 leaves the distribution [TBD]; the workspace is set up for ROS 2 Lyrical and Zenoh.

## SWR-BRG-011: Lifecycle: The rover_bringup shall be started automatically at power-up and bring the platform to ... (Functional)
The rover_bringup shall be started automatically at power-up and bring the platform to the Idle state within [TBD per SYS-SR-024] s.
- Rationale: SYS-SR-024 requires automatic start and a bounded time to Idle.

## SWR-BRG-012: Interface: The rover_bringup shall start foxglove_bridge as node rover_foxglove_bridge (WebSocket ... (Functional)
The rover_bringup shall start foxglove_bridge as node rover_foxglove_bridge (WebSocket port 8765, upstream default) with sysinfo disabled and an asset URI allowlist accepting package:// URIs of the upstream mesh/image extensions in any letter case.
- Rationale: Foxglove, the drive UI and the Cockpit diagnostics page connect through this bridge; upper-case mesh extensions must load.

## SWR-BRG-013: Performance: The rover_bringup shall restrict foxglove_bridge to the whitelisted topics (/tf, /tf_st... (Functional)
The rover_bringup shall restrict foxglove_bridge to the whitelisted topics (/tf, /tf_static and the listed UI topics under any namespace) and to the whitelisted services, unless ROVER_PLATFORM_FOXGLOVE_TOPIC_WHITELIST or ROVER_PLATFORM_FOXGLOVE_SERVICE_WHITELIST is set non-empty.
- Rationale: Anything a browser subscribes to crosses the Zenoh router at full rate; unknown services caused log floods. Topics a UI only publishes must still be listed or its client sends nothing.

## SWR-BRG-014: Interface: The rover_bringup shall start rosbridge_websocket as node rover_rosbridge_websocket (po... (Functional)
The rover_bringup shall start rosbridge_websocket as node rover_rosbridge_websocket (port 9090, upstream default) and rosapi_node as /rosapi.
- Rationale: ros-mcp-server and other rosbridge clients use port 9090 and the /rosapi/* services.

## SWR-BRG-015: Lifecycle: The rover_bringup shall have an automated launch test that verifies the two-stage start... (Functional)
The rover_bringup shall have an automated launch test that verifies the two-stage start order and that all platform nodes are running after start-up.
- Rationale: Start-up order and completeness (SYS-SR-024) are currently checked only by hand.
