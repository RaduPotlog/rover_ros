# SWRS_LED
rover_led Software Requirements Specification (ROVER-A1-ROVER_LED-SWRS-V-001). rover_led drives the rover's two SK9822 LED bumper panels (front = UDP channel 1, rear = UDP channel 2). The LedControllerNode component loads an animation catalog, composites layered image animations (ERROR > ALERT > INFO > STATE) per segment and publishes one RGBA frame per panel; the lifecycle LedDriverNode component validates and encodes those frames into SK9822 packets with a global brightness and hands them to two rover_udp_driver UdpSenderNode components, all composed in rover_led_container. rover_led provides the LED display capability and the animation catalog; the choice of which animation represents the current system state is made by its client (rover_safety's rover_led_safety_node), outside this package.

## SWR-LED-001: Functional: The rover_led shall give every LED segment four animation layers, ERROR (priority 0), A... (Functional)
The rover_led shall give every LED segment four animation layers, ERROR (priority 0), ALERT (1), INFO (2) and STATE (3), and shall composite them into one frame with ERROR on top, alpha-blending each layer over the layers below it.
- Rationale: Lets independent clients show a state, an informational overlay, a transient alert and an error at the same time without overwriting each other; the highest-severity layer stays visible.

## SWR-LED-002: Functional: The rover_led shall play ALERT-layer animations one after another in FIFO order from a ... (Functional)
The rover_led shall play ALERT-layer animations one after another in FIFO order from a queue of at most 10 entries per segment, and shall reject (not queue) a request on a segment whose queue is full while still answering the service call with success=true and a message naming the number of segments that dropped it.
- Rationale: Short alerts (blinkers, goal achieved/failed, charger inserted) must not cancel one another; a bounded queue keeps memory and latency bounded.

## SWR-LED-003: Interface: The rover_led shall provide the service led/set_animation (rover_msgs/SetLedAnimation) ... (Functional)
The rover_led shall provide the service led/set_animation (rover_msgs/SetLedAnimation) that starts the catalog animation with the requested id, param and repeating flag on every segment the catalog entry names, at the entry's priority layer, and shall return success=false with a reason for an unknown id, an unknown segment, an unavailable animation type or an animation that fails to initialise, leaving the current animations unchanged in those cases.
- Rationale: Single command interface for all LED clients; failed requests must not blank the panels.

## SWR-LED-004: Interface: The rover_led shall provide the service led/stop_animation (rover_msgs/StopLedAnimation... (Functional)
The rover_led shall provide the service led/stop_animation (rover_msgs/StopLedAnimation) that removes the animation with the requested id, including its queued ALERT copies, from its layer on every segment, and shall return success=false when that animation is not playing on any segment.
- Rationale: Clients need to clear a repeating state or info animation explicitly, e.g. when a condition ends.

## SWR-LED-005: Performance: The rover_led shall publish one led/channel_<n>_frame (sensor_msgs/Image, encoding rgba... (Functional)
The rover_led shall publish one led/channel_<n>_frame (sensor_msgs/Image, encoding rgba8, height = panel rows, width = LEDs per row, data in wire order, KEEP_LAST depth 10) per configured panel at controller_frequency, default 50.0 Hz.
- Rationale: Animations are sampled at a fixed render rate; the driver forwards each frame to the LED board.

## SWR-LED-006: Interface: The rover_led shall publish led/state (rover_msgs/LedState, reliable, transient-local, ... (Functional)
The rover_led shall publish led/state (rover_msgs/LedState, reliable, transient-local, depth 1) at state_publish_rate, default 5.0 Hz, reporting for every segment and every layer whether it is active and, if so, the animation id, name, param, repeating flag, progress and number of queued animations.
- Rationale: Makes the displayed LED state observable to UIs, logging and verification of the state-to-LED mapping.

## SWR-LED-007: Interface: The rover_led shall publish the loaded animation catalog once at start-up on led/animat... (Functional)
The rover_led shall publish the loaded animation catalog once at start-up on led/animations (rover_msgs/LedAnimationCatalog, reliable, transient-local, depth 1) with the id, name and priority of every entry, sorted by id.
- Rationale: UIs and clients discover the available animations without reading the YAML file.

## SWR-LED-008: Interface: The rover_led shall publish each panel frame additionally on led/channel_<n>_preview (s... (Functional)
The rover_led shall publish each panel frame additionally on led/channel_<n>_preview (sensor_msgs/Image, best effort, depth 1) at preview_publish_rate, default 5.0 Hz, and shall create no preview topics when preview_publish_rate is 0.
- Rationale: UIs (Cockpit LED page) get a low-rate copy so the 50 Hz frames do not cross the Zenoh router.

## SWR-LED-009: Parameter: The rover_led shall load the panel layout and animation catalog from the file given by ... (Functional)
The rover_led shall load the panel layout and animation catalog from the file given by animations_config_path (mandatory, non-empty) and, for rover_a1, shall configure two panels (channel 1 front, channel 2 rear) of 40 LEDs folded into 2 rows each and a catalog containing every rover_msgs/LedAnimation id from 0 (E_STOP) to 17 (FLOOD_LIGHT).
- Rationale: Every named animation id used by clients must exist in the shipped catalog, and the frame geometry must match the physical panels.

## SWR-LED-010: Functional: The rover_led shall provide a catalog animation for each of the SYS-SR-010 states Emerg... (Functional)
The rover_led shall provide a catalog animation for each of the SYS-SR-010 states Emergency Stop (E_STOP, id 0, STATE layer), Idle (READY, id 1, STATE), Teleoperation (MANUAL_ACTION, id 4, STATE), Autonomous (AUTONOMOUS_READY id 11 and AUTONOMOUS_ACTION id 12, STATE), Fault (ERROR, id 2, ERROR layer) and Low Battery (LOW_BATTERY id 5 and CRITICAL_BATTERY id 6, INFO layer).
- Rationale: SYS-SR-009 requires a state-dependent LED indication; rover_led supplies the displayable pattern per state, its client selects it.

## SWR-LED-011: Functional: The rover_led shall encode each RGBA panel frame as an SK9822 packet: a 4-byte start fr... (Functional)
The rover_led shall encode each RGBA panel frame as an SK9822 packet: a 4-byte start frame of 0x00, one 4-byte word per LED of 0xE0 | 5-bit brightness (pixel alpha x global brightness level 0-31 / 255) followed by blue, green and red after gamma 2.2 correction scaled to 240/255/245, and a 4-byte end frame of 0xFF, each word rotated left by one byte for the UDP LED bridge.
- Rationale: Wire format expected by the SK9822 LED board behind the UDP bridge; gamma and white-balance correction give perceptually correct colours.

## SWR-LED-012: Functional: The rover_led shall drop, without sending, any received panel frame that is older than ... (Functional)
The rover_led shall drop, without sending, any received panel frame that is older than frame_timeout (default and rover_a1 value 0.1 s), older than the previously received frame, not rgba8-encoded, or whose height x width or data size does not match the channel's LED count, and shall report each dropped frame as a WARN diagnostic broadcast.
- Rationale: Stale or malformed frames must never reach the LED board; out-of-order delivery must not show an old state.

## SWR-LED-013: Interface: The rover_led shall subscribe to led/channel_1_frame and led/channel_2_frame (sensor_ms... (Functional)
The rover_led shall subscribe to led/channel_1_frame and led/channel_2_frame (sensor_msgs/Image, depth 5) and publish the encoded packets on udp_write/led_channel_1 and udp_write/led_channel_2 (udp_msgs/UdpPacket, depth 5), sized by channel_1_num_led and channel_2_num_led (40 each for rover_a1).
- Rationale: Decouples rendering from the transport; rover_udp_driver sends each channel's packets to its LED board.

## SWR-LED-014: Interface: The rover_led shall provide the service led/set_brightness (rover_msgs/SetLedBrightness... (Functional)
The rover_led shall provide the service led/set_brightness (rover_msgs/SetLedBrightness) accepting a global brightness in [0.0, 1.0], shall reject values outside that range with success=false and unchanged brightness, shall store an accepted value in the global_brightness parameter so it survives a reconfigure, and shall publish the brightness in effect on led/brightness (std_msgs/Float32, reliable, transient-local, depth 1) on activation and after each change.
- Rationale: Operators dim the LEDs (e.g. indoors) at run time; the latched topic lets UIs show the current value.

## SWR-LED-015: Lifecycle: The rover_led driver shall be a managed lifecycle node that, with autostart=true (defau... (Functional)
The rover_led driver shall be a managed lifecycle node that, with autostart=true (default), configures and activates itself once when the executor first spins, forwards frames only while Active, sends an all-off frame to both panels on activation and on deactivation, and on context shutdown finalizes itself (clearing the LEDs) within 1 s.
- Rationale: The LEDs must not keep showing a stale pattern when the driver stops, and must start in a known (dark) state.

## SWR-LED-016: Functional: The rover_led driver shall, when led_control_handshake is true, request LED control fro... (Functional)
The rover_led driver shall, when led_control_handshake is true, request LED control from hardware/led_control_enable (std_srvs/SetBool) on activation, retrying from a 100 ms timer for at most 3 attempts with a 3 s response timeout each, ignore frames until control is granted, release control on deactivation, and hand back a grant that arrives for an earlier activation.
- Rationale: Arbitrates the LED board with a hardware controller that may also drive the LEDs; stale grants must not leave control held by an inactive driver.

## SWR-LED-017: Diagnostics: The rover_led controller shall publish on diagnostics, hardware id Bumper Led, a Led co... (Functional)
The rover_led controller shall publish on diagnostics, hardware id 'Bumper Led', a 'Led controller status' that is ERROR when rendering fails, WARN when a segment fails to update or a catalog animation uses an unavailable type, and OK otherwise (reporting animations loaded, catalog warnings, last rejected request and what each segment shows), plus a 'Led render rate' frequency status expecting controller_frequency with 10 % tolerance over a 10-sample window.
- Rationale: Makes LED subsystem faults visible in the aggregated diagnostics.

## SWR-LED-018: Diagnostics: The rover_led driver shall publish on diagnostics, hardware id Bumper Led, a Led driver... (Functional)
The rover_led driver shall publish on diagnostics, hardware id 'Bumper Led', a 'Led driver status' that is ERROR 'Driver is not active!' when not Active, WARN 'Driver is not yet functional!' while LED control is pending, ERROR when obtaining control failed, and OK 'Driver is fully functional.' when control is granted, including the lifecycle state and LED control status.
- Rationale: A driver that did not come up (autostart has no retry) must be visible to the operator.

## SWR-LED-019: Build: The rover_led launch file rover_led.launch.py shall load rover_led_driver, rover_led_co... (Functional)
The rover_led launch file rover_led.launch.py shall load rover_led_driver, rover_led_controller and two rover_udp_driver UdpSenderNode components (rover_udp_led_channel_1_sender_node to 192.168.77.202:3334 and rover_udp_led_channel_2_sender_node to 192.168.77.201:3333, autostart) into one container rover_led_container with intra-process communication, shall omit the driver and senders when use_sim is True, and shall shut down the launch when the container exits.
- Rationale: Keeps the 50 Hz frame and packet traffic in-process instead of crossing the Zenoh router; simulation has no LED board.

## SWR-LED-020: Functional: The rover_led shall provide a catalog animation (and a matching rover_msgs/LedAnimation... (Functional)
The rover_led shall provide a catalog animation (and a matching rover_msgs/LedAnimation constant) for the SYS-SR-010 Boot state, shown on both panels from the moment the LED driver becomes Active until a client selects another state animation.
- Rationale: SYS-SR-009 requires every SYS-SR-010 state, including Boot, to have a defined LED indication; today the panels stay blank until rover_safety sends the first animation.

## SWR-LED-021: Functional: The rover_led shall document, in the package, the state-to-LED mapping required by SYS-... (Functional)
The rover_led shall document, in the package, the state-to-LED mapping required by SYS-SR-009: for each SYS-SR-010 state the animation id, layer, colour and pattern (steady/blinking/moving, period) shown on the front and rear panels.
- Rationale: SYS-SR-009 acceptance requires a specified colour/pattern per state to test against; today colour and pattern exist only implicitly in the PNG images referenced by the catalog.
