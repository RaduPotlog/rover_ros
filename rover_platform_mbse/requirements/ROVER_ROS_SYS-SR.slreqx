# ROVER_ROS_SYS-SR
ROVER-A1 rover_ros platform system requirements, imported from system/ROVER-A1-ROVER_ROS_SYS-SR-V-002.xlsx (the master). Re-run build_requirements after editing the xlsx.

## SYS-SR-001: Physical: The rover platform shall have a total mass not exceeding 60 kg, including batteries and... (Functional)
The rover platform shall have a total mass not exceeding 60 kg, including batteries and excluding payload.
- Rationale: Limits transport/handling effort and drive-train sizing.

## SYS-SR-002: Drive: The rover platform shall control 4 wheel drive joints in velocity mode using encoder fe... (Functional)
The rover platform shall control 4 wheel drive joints in velocity mode using encoder feedback, at a control rate of at least 50 Hz.
- Rationale: Closed-loop wheel velocity control is required for kinematics and odometry.

## SYS-SR-003: Drive: The rover platform shall implement skid-steer (differential-drive) kinematics that conv... (Functional)
The rover platform shall implement skid-steer (differential-drive) kinematics that convert commanded body linear and angular velocity into wheel velocities, and shall publish wheel odometry.
- Rationale: Allows motion to be commanded as a body twist and position to be estimated.

## SYS-SR-004: Performance: The rover platform shall limit linear velocity to a maximum of 1.0 m/s and angular velo... (Functional)
The rover platform shall limit linear velocity to a maximum of 1.0 m/s and angular velocity to a maximum of 1.7 rad/s, for commands from any source.
- Rationale: Safety speed limit for operation around people.

## SYS-SR-005: Command: The rover platform shall accept velocity commands from 4 sources ([TBD] e.g. joystick t... (Functional)
The rover platform shall accept velocity commands from 4 sources ([TBD] e.g. joystick teleoperation, remote/web UI, navigation stack, autonomy/docking) and shall execute only the highest-priority active source.
- Rationale: Several operators and subsystems may command the rover; conflicts must be resolved in a known, fixed order.

## SYS-SR-006: Safety: The rover platform shall have at least [TBD] hardware emergency stop button(s) that, wh... (Functional)
The rover platform shall have at least [TBD] hardware emergency stop button(s) that, when pressed, remove drive power independently of software (stop category 0 or 1 per IEC 60204-1, ISO 13850).
- Rationale: A hardware E-stop must work even if the software has failed.

## SYS-SR-007: Safety: The rover platform shall provide a software emergency stop, triggerable through the ROS... (Functional)
The rover platform shall provide a software emergency stop, triggerable through the ROS interface, that commands zero velocity to all drive joints within 100 ms.
- Rationale: Lets remote operators and software monitors stop the rover.

## SYS-SR-008: Safety: After any emergency stop (hardware or software), the rover platform shall remain stoppe... (Functional)
After any emergency stop (hardware or software), the rover platform shall remain stopped until an operator performs an explicit reset; releasing the E-stop alone shall not resume motion.
- Rationale: Prevents unexpected motion after an E-stop is released.

## SYS-SR-009: HMI: The rover platform shall indicate its current system state on the LED panels according ... (Functional)
The rover platform shall indicate its current system state on the LED panels according to a defined state-to-LED mapping (colour and pattern for each state in SYS-SR-010).
- Rationale: Lets people nearby see the rover's state at a glance.

## SYS-SR-010: States: The rover platform shall implement a defined system state machine with at least these s... (Functional)
The rover platform shall implement a defined system state machine with at least these states: Boot, Idle, Teleoperation, Autonomous, Emergency Stop, Fault, Low Battery.
- Rationale: SYS-SR-009 and the safety behaviour depend on well-defined states.

## SYS-SR-011: Safety: The rover platform shall bring itself to a stop if no valid velocity command is receive... (Functional)
The rover platform shall bring itself to a stop if no valid velocity command is received from the active source within 500 ms.
- Rationale: Command watchdog: stops the rover if a source crashes or goes silent.

## SYS-SR-012: Safety: The rover platform shall stop if communication with the operator station is lost for mo... (Functional)
The rover platform shall stop if communication with the operator station is lost for more than [TBD] s.
- Rationale: The rover must not drive on while nobody can supervise it.

## SYS-SR-013: Performance: The rover platform shall limit linear acceleration and deceleration to [TBD] m/s^2 and ... (Functional)
The rover platform shall limit linear acceleration and deceleration to [TBD] m/s^2 and angular acceleration to [TBD] rad/s^2.
- Rationale: Prevents tipping, wheel slip and payload damage.

## SYS-SR-014: Safety: The rover platform shall stop from 1.0 m/s within [TBD] m on flat, dry, hard ground whe... (Functional)
The rover platform shall stop from 1.0 m/s within [TBD] m on flat, dry, hard ground when any emergency stop is triggered.
- Rationale: Needed to size safety zones around the rover.

## SYS-SR-015: Power: The rover platform shall operate continuously for at least [TBD] h on a full battery ch... (Functional)
The rover platform shall operate continuously for at least [TBD] h on a full battery charge under a [TBD] duty cycle.
- Rationale: Sets battery capacity and the mission length.

## SYS-SR-016: Power: The rover platform shall publish battery voltage, current and state of charge at 1 Hz o... (Functional)
The rover platform shall publish battery voltage, current and state of charge at 1 Hz or faster.
- Rationale: Needed by operators and for low-battery behaviour.

## SYS-SR-017: Power: The rover platform shall enter the Low Battery state at [TBD]% state of charge and shal... (Functional)
The rover platform shall enter the Low Battery state at [TBD]% state of charge and shall perform a safe stop at [TBD]% state of charge.
- Rationale: Prevents deep discharge and loss of control.

## SYS-SR-018: Power: The rover platform shall support battery charging via [TBD: external connector / dockin... (Functional)
The rover platform shall support battery charging via [TBD: external connector / docking station] without removing the battery.
- Rationale: Practical daily operation.

## SYS-SR-019: Sensors: The rover platform shall include an IMU that publishes orientation, angular velocity an... (Functional)
The rover platform shall include an IMU that publishes orientation, angular velocity and linear acceleration at 100 Hz or faster.
- Rationale: Improves odometry and allows tilt/tip-over detection.

## SYS-SR-020: Software: The rover platform software shall be based on ROS 2 [TBD distribution] and shall use ro... (Functional)
The rover platform software shall be based on ROS 2 [TBD distribution] and shall use ros2_control for the drive hardware interface.
- Rationale: Fixes the software baseline and interfaces.

## SYS-SR-021: Software: The rover platform shall follow ROS REP-103 (units and conventions) and REP-105 (coordi... (Functional)
The rover platform shall follow ROS REP-103 (units and conventions) and REP-105 (coordinate frames: map, odom, base_link).
- Rationale: Keeps the rover compatible with standard ROS navigation tools.

## SYS-SR-022: Software: The rover platform shall publish diagnostic status for drive motors, battery, E-stop ci... (Functional)
The rover platform shall publish diagnostic status for drive motors, battery, E-stop circuit and sensors on /diagnostics at 1 Hz or faster.
- Rationale: Supports fault detection and maintenance.

## SYS-SR-023: Safety: The rover platform shall publish the state of the hardware and software emergency stops... (Functional)
The rover platform shall publish the state of the hardware and software emergency stops on a ROS topic within 100 ms of a change.
- Rationale: Operators and software need to know the E-stop state.

## SYS-SR-024: Software: The rover platform shall start all platform software automatically on power-up and reac... (Functional)
The rover platform shall start all platform software automatically on power-up and reach the Idle state within [TBD] s.
- Rationale: The rover must be usable without manual login or setup.

## SYS-SR-025: Communication: The rover platform shall provide a wireless link to the operator station with a line-of... (Functional)
The rover platform shall provide a wireless link to the operator station with a line-of-sight range of at least [TBD] m and a round-trip latency of at most [TBD] ms.
- Rationale: Required for teleoperation and monitoring.

## SYS-SR-026: Physical: The rover platform shall not exceed [TBD] x [TBD] x [TBD] mm (L x W x H). (Functional)
The rover platform shall not exceed [TBD] x [TBD] x [TBD] mm (L x W x H).
- Rationale: Must fit through doors and in transport vehicles.

## SYS-SR-027: Physical: The rover platform shall carry a payload of at least [TBD] kg while still meeting SYS-S... (Functional)
The rover platform shall carry a payload of at least [TBD] kg while still meeting SYS-SR-004 and SYS-SR-014.
- Rationale: Defines what the platform is useful for.

## SYS-SR-028: Environment: The rover platform shall operate on slopes up to [TBD] degrees on [TBD] terrain types. (Functional)
The rover platform shall operate on slopes up to [TBD] degrees on [TBD] terrain types.
- Rationale: Defines the operating domain.

## SYS-SR-029: Environment: The rover platform shall operate at ambient temperatures from [TBD] to [TBD] degC and s... (Functional)
The rover platform shall operate at ambient temperatures from [TBD] to [TBD] degC and shall meet ingress protection IP[TBD].
- Rationale: Defines the environmental envelope for outdoor use.
