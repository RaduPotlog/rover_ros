# SWRS_MSG
rover_msgs Software Requirements Specification (ROVER-A1-ROVER_MSGS-SWRS-V-001). rover_msgs defines the custom ROS 2 messages and services of the Rover A1 stack. The safety-relevant contracts are SafetyStatus (plant state of the E-Stop chain, the only message that may permit motion), SafetyCommandEcho (read-backs of software-driven safety coils, inhibit-only), AuxIoState (non-safety PLC IO), RoverDriverState and its nested DriverStateNamed / DriverState / FaultFlag / RuntimeError (motor driver health), RcLinkStatus (RC link quality), ChargingStatus and the LED animation catalogue. Safety commands are deliberately not messages: they are std_srvs/Trigger services served by rover_hardware_interface.

## SWR-MSG-001: Interface: The rover_msgs shall define rover_msgs/SafetyStatus with fields std_msgs/Header header,... (Functional)
The rover_msgs shall define rover_msgs/SafetyStatus with fields std_msgs/Header header, builtin_interfaces/Time io_sample_time, bool hw_e_stop_user_button, bool motor_contactor_engaged, bool latch_active, uint8 latch_cause and bool link_healthy.
- Rationale: SYS-SR-023 requires the HW and SW E-Stop state on a ROS topic; this is the plant-state half of the old GpioState and the only safety message consumers may gate motion on.

## SWR-MSG-002: Interface: The rover_msgs shall document in SafetyStatus that hw_e_stop_user_button true means pre... (Functional)
The rover_msgs shall document in SafetyStatus that hw_e_stop_user_button true means pressed, motor_contactor_engaged true means contacts closed (drive live), latch_active true means the E-Stop latch holds a stop, and link_healthy false means the other fields are last-known-good values that must not be trusted.
- Rationale: Unambiguous field semantics (including the inverted sense of motor_contactor_engaged) prevent consumers from gating on the wrong polarity (SYS-SR-023, SYS-SR-022).

## SWR-MSG-003: Interface: The rover_msgs shall define SafetyStatus.io_sample_time as the time the safety PLC was ... (Functional)
The rover_msgs shall define SafetyStatus.io_sample_time as the time the safety PLC was polled, distinct from header.stamp (the publish time), for use by consumer staleness checks.
- Rationale: Staleness must measure data age, not transport age (SYS-SR-023 latency, SYS-SR-022).

## SWR-MSG-004: Interface: The rover_msgs shall define the SafetyStatus latch_cause constants LATCH_CAUSE_UNKNOWN ... (Functional)
The rover_msgs shall define the SafetyStatus latch_cause constants LATCH_CAUSE_UNKNOWN = 0, LATCH_CAUSE_SW_USER_BUTTON = 1, LATCH_CAUSE_SW_MOTOR_DRIVER_FAULT = 2, LATCH_CAUSE_CPU_WATCHDOG = 3 and LATCH_CAUSE_HW_USER_BUTTON = 4.
- Rationale: Lets consumers and logs report why the rover stopped once the PLC exposes the trip source (SYS-SR-023, SYS-SR-022).

## SWR-MSG-005: Safety: The rover_msgs shall define rover_msgs/SafetyCommandEcho (header, io_sample_time, sw_e_... (Functional)
The rover_msgs shall define rover_msgs/SafetyCommandEcho (header, io_sample_time, sw_e_stop_user_button, sw_e_stop_motor_driver_fault, sw_e_stop_latch_reset, cpu_wdg_heartbeat) and document that its fields may be used only to inhibit motion, never to permit it, and that cpu_wdg_heartbeat and sw_e_stop_latch_reset carry no stop state.
- Rationale: Separating command echoes from plant state is what stops a consumer from treating "we asked for a stop" as evidence the hardware stopped (SAFETY_CHAIN.md §4); gating on the heartbeat once made a motion lock oscillate.

## SWR-MSG-006: Interface: The rover_msgs shall not define any message type that carries a safety command (E-Stop ... (Functional)
The rover_msgs shall not define any message type that carries a safety command (E-Stop set, E-Stop reset or latch reset).
- Rationale: A safety command needs an acknowledgement and must never be replayed to a late joiner, so it is a service (std_srvs/Trigger) and not a topic (SYS-SR-007, SAFETY_CHAIN.md §4).

## SWR-MSG-007: Interface: The rover_msgs shall define rover_msgs/AuxIoState with header, io_sample_time, bool[6] ... (Functional)
The rover_msgs shall define rover_msgs/AuxIoState with header, io_sample_time, bool[6] inputs (PLC DIO06..DIO11), bool[6] outputs (read-back of DIO00..DIO05) and link_healthy, documented as outside the safety chain.
- Rationale: General-purpose PLC IO must be available without anyone gating motion on it.

## SWR-MSG-008: Interface: The rover_msgs shall define rover_msgs/RoverDriverState (header, DriverStateNamed[] dri... (Functional)
The rover_msgs shall define rover_msgs/RoverDriverState (header, DriverStateNamed[] driver_states, bool error) whose DriverState carries current, temperature, FaultFlag (emergency_stop, motor_setup_fault), RuntimeError (safety_stop_active), motor_states_data_timed_out, driver_state_data_timed_out, comm_error and heartbeat_timeout.
- Rationale: Drive-motor health reporting (SYS-SR-022).

## SWR-MSG-009: Interface: The rover_msgs shall define rover_msgs/RcLinkStatus carrying the CRSF LINK_STATISTICS u... (Functional)
The rover_msgs shall define rover_msgs/RcLinkStatus carrying the CRSF LINK_STATISTICS uplink RSSI (both antennas), uplink_link_quality (0-100 %), uplink SNR, active antenna, rf_mode, uplink TX power and the downlink RSSI, link quality and SNR.
- Rationale: Uplink link quality is what gates teleop, i.e. the observable for SYS-SR-012 loss of the operator link on the RC path.

## SWR-MSG-010: Interface: The rover_msgs shall define rover_msgs/LedAnimation animation ids covering every SYS-SR... (Functional)
The rover_msgs shall define rover_msgs/LedAnimation animation ids covering every SYS-SR-010 system state, including a Boot state.
- Rationale: SYS-SR-009 requires a defined state-to-LED mapping for each SYS-SR-010 state (Boot, Idle, Teleoperation, Autonomous, Emergency Stop, Fault, Low Battery).

## SWR-MSG-011: Interface: The rover_msgs shall define a system-state message whose state constants enumerate at l... (Functional)
The rover_msgs shall define a system-state message whose state constants enumerate at least Boot, Idle, Teleoperation, Autonomous, Emergency Stop, Fault and Low Battery.
- Rationale: SYS-SR-010 requires a defined system state machine whose transitions can be observed; no rover_msgs type carries it.

## SWR-MSG-012: Build: The rover_msgs shall generate all messages and services with rosidl_generate_interfaces... (Functional)
The rover_msgs shall generate all messages and services with rosidl_generate_interfaces depending only on builtin_interfaces, geometry_msgs and std_msgs, and export rosidl_default_runtime.
- Rationale: Keeps the interface package light so every node can depend on it (SYS-SR-020 ROS 2 based software).
