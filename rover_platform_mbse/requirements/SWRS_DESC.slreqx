# SWRS_DESC
rover_description Software Requirements Specification (ROVER-A1-ROVER_DESCRIPTION-SWRS-V-001). rover_description holds the URDF/xacro model of Rover A1: the kinematic tree and frames (REP-103/105), wheel geometry and joint limits, inertial properties, meshes, sensor mount frames, the simulation sensors and battery, and the <ros2_control> blocks that select and parameterise the hardware plugins (RoverA1System, PhidgetImuSensor) or gz_ros2_control in simulation. All hardware-interface timing and drive-train parameters are URDF <param> tags here. Its launch file generates the URDF and runs robot_state_publisher, which publishes robot_description and the static/joint TF.

## SWR-DESC-001: Build: The rover_description shall generate the rover_a1 robot description from urdf/rover_a1.... (Functional)
The rover_description shall generate the rover_a1 robot description from urdf/rover_a1.urdf.xacro with the xacro arguments use_sim, namespace, wheel_config_file, battery_config_file, controller_config_file, imu_xyz/imu_rpy, lidar_xyz/lidar_rpy and gps_xyz/gps_rpy.
- Rationale: A single parameterised model serves hardware and simulation (SYS-SR-020 ros2_control based software).

## SWR-DESC-002: Interface: The rover_description shall define the frame tree base_footprint -> base_link -> body_l... (Functional)
The rover_description shall define the frame tree base_footprint -> base_link -> body_link with imu_link, lidar_link, gps_link and the four <prefix>_wheel_base_link / <prefix>_wheel_link frames as children of body_link, using REP-103 axes (+x forward, +y left, +z up) and prefixing every frame with "<namespace>/" when a namespace is set.
- Rationale: SYS-SR-021 requires REP-103 conventions and REP-105 frames; base_footprint is the ground projection the odometry filters publish odom -> base_footprint to.

## SWR-DESC-003: Functional: The rover_description shall place base_link above base_footprint by tyre_radius minus t... (Functional)
The rover_description shall place base_link above base_footprint by tyre_radius minus the wheel axis height above body_link (0.037363 m), with base_link coincident with body_link.
- Rationale: Keeps base_footprint on the ground plane (REP-105 2D navigation, SYS-SR-021).

## SWR-DESC-004: Parameter: The rover_description shall take wheel geometry only from config/wheel_01.yaml (tyre_ra... (Functional)
The rover_description shall take wheel geometry only from config/wheel_01.yaml (tyre_radius 0.1699 m, wheel_width 0.108 m, wheelbase 0.503 m, wheel_separation 0.617 m, tyre_y_offset -0.00171 m) and mount the fl, fr, rl and rr wheels at (+/-wheelbase/2, +/-wheel_separation/2) in their REP-103 quadrants at a common height, with each tyre collision cylinder |tyre_y_offset| inboard of its joint.
- Rationale: Single source of truth for kinematic geometry used by the URDF and (via its test) by the drive controller (SYS-SR-003).

## SWR-DESC-005: Parameter: The rover_description shall model each wheel joint as a continuous joint about +y with ... (Functional)
The rover_description shall model each wheel joint as a continuous joint about +y with limit effort 64.5 and velocity 10.958 rad/s, so that a positive joint velocity drives the rover forward.
- Rationale: Uniform joint sign for all four wheels (no negated axis) and a velocity limit that the drive controller limits are checked against (SYS-SR-002, SYS-SR-004).

## SWR-DESC-006: Interface: The rover_description shall declare, with use_sim false, a <ros2_control> system compon... (Functional)
The rover_description shall declare, with use_sim false, a <ros2_control> system component named "rover_system_node" (no namespace prefix: its node is rover_system_node in the controller manager's namespace, e.g. /rover/rover_system_node) using plugin rover_hardware_interface/RoverA1System with the four wheel joints each exposing a velocity command interface and position, velocity and effort state interfaces, and with use_sim true the plugin gz_ros2_control/GazeboSimSystem with the same joints plus the IMU state interfaces.
- Rationale: SYS-SR-002 (4 joints, velocity mode, encoder feedback) and SYS-SR-020 (ros2_control hardware interface).

## SWR-DESC-007: Parameter: The rover_description shall set the RoverA1System safety-link parameters modbus_host 19... (Functional)
The rover_description shall set the RoverA1System safety-link parameters modbus_host 192.168.88.11, modbus_port 502, modbus_connection_retry_count 0, modbus_connection_retry_delay_ms 1000, modbus_response_timeout_ms 150, safety_wdg_kick_period_ms 200, safety_io_poll_period_ms 100 and safety_latch_reset_pulse_ms 100.
- Rationale: These values bound the E-Stop heartbeat and state latency (SYS-SR-006, SYS-SR-023); the response timeout must stay under the kick period so one stalled transaction cannot eat a heartbeat tick.

## SWR-DESC-008: Parameter: The rover_description shall set the RoverA1System drive-train parameters driver_states_... (Functional)
The rover_description shall set the RoverA1System drive-train parameters driver_states_update_frequency 20.0, max_rover_driver_initialization_attempts 3, max_rover_driver_activation_attempts 3, the three error-filter counts 2, driver_comm_timeout_ms 300, motor_failsafe_timeout_ms 500, motor_acceleration 4.0, motor_current_limit 15.0, motor_supply_voltage 24.0, motor_torque_constant 0.11, max_rpm_motor_speed 2800, gear_ratio 23.3, gearbox_efficiency 0.70, raw_current_to_amps_scale 0.001 and encoder_resolution 1024.
- Rationale: Drive actuation and feedback scaling (SYS-SR-002) and the DCC1000 command-loss failsafe (SYS-SR-011).

## SWR-DESC-009: Parameter: The rover_description shall set the E-Stop reset tolerances velocity_command_zero_toler... (Functional)
The rover_description shall set the E-Stop reset tolerances velocity_command_zero_tolerance 0.4 rad/s and velocity_state_zero_tolerance 0.05 rad/s.
- Rationale: SYS-SR-008: the SW E-Stop cannot be reset while commanded to move or still rolling; 0.4 rad/s is the smallest value above the wheel PID i_clamp_max (0.33 rad/s).

## SWR-DESC-010: Parameter: The rover_description shall declare, with use_sim false, a <ros2_control> sensor compon... (Functional)
The rover_description shall declare, with use_sim false, a <ros2_control> sensor component "rover_imu" (no namespace prefix: its node is rover_imu in the controller manager's namespace, e.g. /rover/rover_imu) using plugin rover_hardware_interface/PhidgetImuSensor with data_interval_ms 8, callback_delta_epsilon_ms 1, Madgwick gain 0.00304 and zeta 0.00151, use_mag false, stateless false, remove_gravity_vector false and world_frame enu, exporting the 10 orientation / angular_velocity / linear_acceleration state interfaces.
- Rationale: SYS-SR-019 IMU at >= 100 Hz (8 ms = 125 Hz sampling). The magnetometer is disabled because it is uncalibrated near the motors.

## SWR-DESC-011: Functional: The rover_description shall, in rover_load_urdf.launch.py, take the IMU, lidar and GPS ... (Functional)
The rover_description shall, in rover_load_urdf.launch.py, take the IMU, lidar and GPS mount poses from the ROVER_SYSTEM_MOUNT_{IMU,LIDAR,GPS}_{X,Y,Z} and _{ROLL,PITCH,YAW} environment variables, falling back to the defaults (IMU xyz (-0.09, 0.0, 0.2), rpy (3.14159, 0.0, 0.0); lidar and GPS all 0.0) for unset or non-finite values.
- Rationale: Sensor extrinsics are per-rover (balena device variables); a malformed value must not break xacro and take robot_state_publisher down (SYS-SR-021 frames).

## SWR-DESC-012: Parameter: The rover_description shall declare body_link inertial mass 39.5026 kg and each wheel l... (Functional)
The rover_description shall declare body_link inertial mass 39.5026 kg and each wheel link mass 4.79294 kg (58.6744 kg in total).
- Rationale: Inertial properties drive the simulation dynamics; SYS-SR-001 caps the platform mass at 60 kg including batteries and excluding payload.

## SWR-DESC-013: Interface: The rover_description shall start robot_state_publisher as node rover_state_publisher_n... (Functional)
The rover_description shall start robot_state_publisher as node rover_state_publisher_node in the requested namespace with the generated robot_description, frame_prefix "<namespace>/" and use_sim_time equal to use_sim, when publish_robot_state is true (default).
- Rationale: Publishes robot_description and the robot TF tree (SYS-SR-021).

## SWR-DESC-014: Functional: The rover_description shall, with use_sim true, provide Gazebo sensors on the IMU, lida... (Functional)
The rover_description shall, with use_sim true, provide Gazebo sensors on the IMU, lidar and GPS frames: IMU at 50 Hz on <ns>imu/data_raw with gaussian noise, a 16-ring gpu_lidar over +/-15 deg with 720 samples, 0.2-20 m range at 10 Hz on <ns>lidar, and a navsat sensor at 5 Hz on <ns>gps/fix.
- Rationale: Simulation stand-ins for the RS16 lidar, RUTX11 GNSS and Phidgets IMU used by the navigation stack in Gazebo.

## SWR-DESC-015: Performance: The rover_description shall configure the simulated IMU update_rate at 100 Hz or faster. (Functional)
The rover_description shall configure the simulated IMU update_rate at 100 Hz or faster.
- Rationale: SYS-SR-019 requires IMU data at >= 100 Hz; the simulation should exercise the same rate as the hardware target.

## SWR-DESC-016: Parameter: The rover_description shall configure the simulated battery (Gazebo LinearBatteryPlugin... (Functional)
The rover_description shall configure the simulated battery (Gazebo LinearBatteryPlugin) with capacity 40.0 Ah, initial charge 0.7 of capacity, charging_time 8.0 h, power_load 160.0 W and discharging disabled by default.
- Rationale: Simulation of the BAT01 pack for SYS-SR-015 runtime estimates (~6 h at 160 W per the config comment).
