# SWRS_BAT
rover_battery Software Requirements Specification (ROVER-A1-ROVER_BATTERY-SWRS-V-001). rover_battery decodes the Daly BMS telemetry that the ESP32 rover_led_bms_ble_controller forwards over UDP (392-byte payload, received by rover_udp_driver's UdpReceiverNode on 192.168.1.201:4444 in the same component container) and publishes the rover's battery state as sensor_msgs/BatteryState on battery/battery_status and rover_msgs/ChargingStatus on battery/charging_status, with a health classification from the BMS alarm bits, a data watchdog, and diagnostics. It is the battery input of rover_safety (battery E-Stop and shutdown policy, LED battery animations). State-of-charge thresholds live in the BMS configuration, not in this package.

## SWR-BAT-001: Interface: The rover_battery shall subscribe udp_msgs/UdpPacket on battery_udp_data (depth 100), f... (Functional)
The rover_battery shall subscribe udp_msgs/UdpPacket on battery_udp_data (depth 100), fed by the rover_udp_battery_receiver_node bound to ip 192.168.1.201, port 4444.
- Rationale: The ESP32 BMS bridge sends its telemetry as UDP datagrams; the receiver's udp_read is remapped to this topic.

## SWR-BAT-002: Functional: The rover_battery shall decode only payloads of exactly 392 bytes (385-byte BmsData + 7... (Functional)
The rover_battery shall decode only payloads of exactly 392 bytes (385-byte BmsData + 7-byte BmsAlarms) and shall ignore, without publishing and without resetting the watchdog, packets of any other size and all-zero no-data payloads.
- Rationale: The layout mirrors the firmware's packed structs byte for byte; the firmware sends an all-zero payload when it has no BMS data, which must not look like a live BMS.

## SWR-BAT-003: Interface: The rover_battery shall publish sensor_msgs/BatteryState on battery/battery_status (dep... (Functional)
The rover_battery shall publish sensor_msgs/BatteryState on battery/battery_status (depth 5, reliable, volatile) once for every valid BMS frame received.
- Rationale: Primary battery interface of the platform, consumed by rover_safety's battery policy and LED node.

## SWR-BAT-004: Functional: The rover_battery shall fill BatteryState with voltage = pack voltage [V], current = pa... (Functional)
The rover_battery shall fill BatteryState with voltage = pack voltage [V], current = pack current [A], percentage = BMS SOC / 100, charge = residual capacity [Ah] (mAh / 1000), capacity = NaN, design_capacity = design_capacity parameter [Ah], temperature = hottest sensor [degC], cell_voltage [V] (mV / 1000) and cell_temperature for the reported (clamped) cell and sensor counts, technology LIFE, present = true and serial_number from the parameter.
- Rationale: SI units per REP-103 and BatteryState conventions (NaN for unmeasured values); the hottest sensor lets rover_safety see a single hot cell.

## SWR-BAT-005: Functional: The rover_battery shall classify battery health from the BMS alarm bits as DEAD on a le... (Functional)
The rover_battery shall classify battery health from the BMS alarm bits as DEAD on a level-one pack-voltage-low, cell-voltage-low or SOC-low alarm, otherwise OVERVOLTAGE on a level-two pack-voltage-high or SOC-high alarm, and then override the result with OVERHEAT on a level-one charge/discharge temperature-high alarm or COLD on a level-one charge/discharge temperature-low alarm; GOOD when none apply.
- Rationale: Maps the BMS protection state onto BatteryState health values that rover_safety acts on (DEAD/OVERVOLTAGE trip the E-Stop, OVERHEAT is graded by temperature).

## SWR-BAT-006: Functional: The rover_battery shall report power_supply_status NOT_CHARGING for BMS status 0, CHARG... (Functional)
The rover_battery shall report power_supply_status NOT_CHARGING for BMS status 0, CHARGING for status 1 (FULL when SOC >= 100 %), DISCHARGING for status 2 and UNKNOWN otherwise.
- Rationale: Charge state drives the LED charging animations and the charging-overheat error.

## SWR-BAT-007: Interface: The rover_battery shall publish rover_msgs/ChargingStatus on battery/charging_status (d... (Functional)
The rover_battery shall publish rover_msgs/ChargingStatus on battery/charging_status (depth 5) with every battery state, with charging = (BMS status 1), current and current_battery = pack current, and charger_type WIRED while charging, UNKNOWN otherwise.
- Rationale: Separate charging indication for consumers that do not parse BatteryState.

## SWR-BAT-008: Safety: The rover_battery shall, when no valid BMS frame has been received for watchdog_timeout... (Functional)
The rover_battery shall, when no valid BMS frame has been received for watchdog_timeout_ms (10000 ms), publish a BatteryState with present = false, power_supply_health WATCHDOG_TIMER_EXPIRE, power_supply_status UNKNOWN, NaN percentage, charge and capacity, zeroed cell arrays of the last known size, and the error 'Battery watchdog expired', and repeat it every watchdog_timeout_ms while data stays absent.
- Rationale: A lost BMS must become an explicit, safe state: rover_safety trips the E-Stop on WATCHDOG_TIMER_EXPIRE and the LED node shows ERROR; NaN (not 0 %) prevents consumers reading a flat pack.

## SWR-BAT-009: Parameter: The rover_battery shall declare design_capacity (default 40.0 Ah, range [0.1, 1000.0]),... (Functional)
The rover_battery shall declare design_capacity (default 40.0 Ah, range [0.1, 1000.0]), serial_number (default 224KA141600043) and watchdog_timeout_ms (default 10000, range [1, 600000]), and shall fail to start on an out-of-range override.
- Rationale: Pack identity is not reported by the BMS; the watchdog period must be bounded.

## SWR-BAT-010: Diagnostics: The rover_battery shall publish diagnostics under hardware ID RoverBattery with Battery... (Functional)
The rover_battery shall publish diagnostics under hardware ID 'RoverBattery' with 'Battery errors' (STALE before data, ERROR listing every active BMS alarm name or the watchdog error, OK otherwise) and 'Battery status' (present, charge state, health, voltage, current, SOC, charge, design capacity, temperature, cell count, min/max cell voltage and difference).
- Rationale: Battery faults must reach /diagnostics as ERROR per SYS-SR-022.

## SWR-BAT-011: Build: The rover_battery shall, in rover_battery.launch.py, load rover_battery_node and the UD... (Functional)
The rover_battery shall, in rover_battery.launch.py, load rover_battery_node and the UDP receiver as components of one component container (rover_battery_container) with intra-process communication, bringing the lifecycle-managed receiver to ACTIVE through its autostart parameter.
- Rationale: BMS packets never cross the Zenoh router.

## SWR-BAT-012: Performance: The rover_battery shall publish battery/battery_status at 1 Hz or faster regardless of ... (Functional)
The rover_battery shall publish battery/battery_status at 1 Hz or faster regardless of the BMS packet timing, republishing the latest reading on a fixed-rate timer, and shall enter the watchdog state (SWR-BAT-008) when the latest reading is older than [TBD] s.
- Rationale: SYS-SR-016 requires >= 1 Hz; today the topic is published only per UDP packet and the only periodic output is the watchdog state every 10000 ms, so the rate is not guaranteed by this package.

## SWR-BAT-013: Interface: The rover_battery shall set BatteryState.header.stamp to the time the BMS frame was rec... (Functional)
The rover_battery shall set BatteryState.header.stamp to the time the BMS frame was received (or the watchdog fired) and header.frame_id to a battery frame name.
- Rationale: The header is left empty today, so consumers cannot judge the age of a reading from the message itself and rover_safety stamps on arrival.

## SWR-BAT-014: Performance: The rover_battery shall report pack voltage, current and state of charge within 5 % of ... (Functional)
The rover_battery shall report pack voltage, current and state of charge within 5 % of a reference meter.
- Rationale: SYS-SR-016 acceptance criterion; the package passes BMS values through, so the accuracy is that of the BMS plus the conversions.

## SWR-BAT-015: Lifecycle: The rover_battery shall implement rover_battery_node as a managed lifecycle node that c... (Functional)
The rover_battery shall implement rover_battery_node as a managed lifecycle node that creates its subscription, publishers and watchdog timer in configure/activate and is brought to ACTIVE by an autostart parameter.
- Rationale: Project convention: nodes owning a resource are lifecycle-managed so a supervisor can restart them; rover_battery_node is a plain rclcpp::Node today (only the UDP receiver next to it is lifecycle-managed).
