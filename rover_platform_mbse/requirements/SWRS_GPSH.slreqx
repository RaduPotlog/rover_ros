# SWRS_GPSH
rover_gps_heading Software Requirements Specification (ROVER-A1-ROVER_GPS_HEADING-SWRS-V-001). rover_gps_heading provides rover_gps_heading_node, a C++ Clean Architecture node that derives the rover's absolute East-North-Up (ENU) heading from GNSS course while the rover drives straight. It estimates a fixed yaw offset between the local odom frame and ENU from gps/fix and odom, latches it once enough straight segments agree, and then republishes every odom yaw as an ENU heading on gps/heading_imu for rover_navsat_transform_node. It is localization logic, not a GPS driver: the receiver driver and fix-health diagnostics are in the sensor payload (rover_sensors, outside this boundary). It is started by rover_localization in GPS mode.

## SWR-GPSH-001: Interface: The rover_gps_heading shall subscribe to sensor_msgs/NavSatFix on the relative topic gp... (Functional)
The rover_gps_heading shall subscribe to sensor_msgs/NavSatFix on the relative topic gps/fix with QoS reliable, volatile, keep-last depth 10.
- Rationale: GNSS fix is the project's reliable exception to best-effort sensor QoS: rover_gps_driver and the simulation bridge publish reliably, and navsat_transform subscribes reliably.

## SWR-GPSH-002: Interface: The rover_gps_heading shall subscribe to nav_msgs/Odometry on the relative topic odom (... (Functional)
The rover_gps_heading shall subscribe to nav_msgs/Odometry on the relative topic odom (QoS depth 10) and use its orientation yaw, twist.linear.x and twist.angular.z.
- Rationale: The local EKF output (rover_ekf_node) provides the odom-frame yaw, forward speed and yaw rate used for straight-motion detection.

## SWR-GPSH-003: Interface: The rover_gps_heading shall publish sensor_msgs/Imu on gps/heading_imu (QoS depth 10) w... (Functional)
The rover_gps_heading shall publish sensor_msgs/Imu on gps/heading_imu (QoS depth 10) with frame_id heading_frame_id, orientation containing only the ENU yaw (x = y = 0), orientation covariance [0] = [4] = 1.0e3 and [8] = yaw std squared, and angular-velocity and linear-acceleration covariance [0] = -1 (not provided).
- Rationale: navsat_transform_node needs an absolute ENU heading as an Imu message; -1 covariance marks the unused fields per the sensor_msgs convention (REP-103/REP-145 style).

## SWR-GPSH-004: Functional: The rover_gps_heading shall publish gps/heading_imu only after the alignment has reache... (Functional)
The rover_gps_heading shall publish gps/heading_imu only after the alignment has reached the Aligned state and only when publish_heading is true, and then once for every received odom message with yaw = wrap(odom yaw + latched offset).
- Rationale: An unaligned heading would place GPS fixes wrongly in the map frame.

## SWR-GPSH-005: Functional: The rover_gps_heading shall form one course measurement from each straight segment of a... (Functional)
The rover_gps_heading shall form one course measurement from each straight segment of at least alignment.min_segment_length_m (3.0 m) GNSS displacement, as offset = atan2(dNorth, dEast) - circular mean of odom yaw over the segment, adding pi when reversing (vx < 0).
- Rationale: While not turning, the GNSS course equals the ENU heading and the antenna lever arm does not bias it.

## SWR-GPSH-006: Functional: The rover_gps_heading shall treat motion as straight only when |vx| >= alignment.min_sp... (Functional)
The rover_gps_heading shall treat motion as straight only when |vx| >= alignment.min_speed_m_s (0.3 m/s), |yaw rate| <= alignment.max_yaw_rate_rad_s (0.1 rad/s) and the yaw change since segment start is <= alignment.max_yaw_change_rad (0.1 rad), and shall abort the current segment otherwise or when the drive direction changes.
- Rationale: Course equals heading only for straight motion.

## SWR-GPSH-007: Functional: The rover_gps_heading shall ignore a GNSS fix for alignment (and abort the current segm... (Functional)
The rover_gps_heading shall ignore a GNSS fix for alignment (and abort the current segment) when it has no fix status, its horizontal 1-sigma error exceeds alignment.max_horizontal_std_m (5.0 m), the latest odometry is older than alignment.max_odometry_age_s (0.5 s), or the gap to the previous fix exceeds alignment.max_fix_gap_s (2.5 s).
- Rationale: Poor or stale fixes would corrupt the course measurement.

## SWR-GPSH-008: Functional: The rover_gps_heading shall latch the circular mean of the most recent alignment.requir... (Functional)
The rover_gps_heading shall latch the circular mean of the most recent alignment.required_segments (3) offsets as the odom-to-ENU yaw offset when their circular standard deviation is <= alignment.max_offset_std_rad (0.1 rad), and keep it until reset.
- Rationale: Agreement of several independent segments guards against a single bad measurement.

## SWR-GPSH-009: Functional: The rover_gps_heading shall report the published heading standard deviation as max(min_... (Functional)
The rover_gps_heading shall report the published heading standard deviation as max(min_heading_std_rad, latched offset std), with min_heading_std_rad = 0.05 rad by default.
- Rationale: Prevents over-confident heading covariance in navsat_transform and the global EKF.

## SWR-GPSH-010: Interface: The rover_gps_heading shall provide the std_srvs/Trigger service gps/reset_heading_alig... (Functional)
The rover_gps_heading shall provide the std_srvs/Trigger service gps/reset_heading_alignment that discards the alignment, returns success true with the message 'Heading alignment reset; drive straight to realign.', and immediately republishes the (unaligned) alignment status.
- Rationale: Lets the operator realign after a heading error without restarting the node.

## SWR-GPSH-011: Diagnostics: The rover_gps_heading shall publish a Heading alignment diagnostic (hardware ID RoverGp... (Functional)
The rover_gps_heading shall publish a 'Heading alignment' diagnostic (hardware ID 'RoverGpsHeading') with keys State, Accepted segments, Heading output and, once available, Yaw offset (deg) and Offset std (deg), updated by a 1 s timer and immediately at startup and on alignment.
- Rationale: Shows the operator whether GPS fusion has an absolute heading (SYS-SR-022 sensor diagnostics).

## SWR-GPSH-012: Diagnostics: The rover_gps_heading shall grade the Heading alignment diagnostic OK when aligned, OK ... (Functional)
The rover_gps_heading shall grade the 'Heading alignment' diagnostic OK when aligned, OK when unaligned with publish_heading false, and WARN ('Drive straight to align the GNSS heading.') when unaligned with publish_heading true.
- Rationale: An unaligned heading is only a fault when GPS fusion depends on it.

## SWR-GPSH-013: Parameter: The rover_gps_heading shall declare publish_heading (default true), min_heading_std_rad... (Functional)
The rover_gps_heading shall declare publish_heading (default true), min_heading_std_rad (default 0.05, positive, max 3.2), heading_frame_id (default base_link) and the alignment.* parameters with the defaults min_segment_length_m 3.0, min_speed_m_s 0.3, max_yaw_rate_rad_s 0.1, max_yaw_change_rad 0.1, max_horizontal_std_m 5.0, max_fix_gap_s 2.5, max_odometry_age_s 0.5, required_segments 3 (range 1-100) and max_offset_std_rad 0.1.
- Rationale: Declared, bounded parameters prevent silent misconfiguration.

## SWR-GPSH-014: Lifecycle: The rover_gps_heading shall validate the alignment configuration at construction, rejec... (Functional)
The rover_gps_heading shall validate the alignment configuration at construction, rejecting non-positive limits or required_segments = 0, and shall then exit with code 1 and a FATAL log.
- Rationale: Fail fast on inconsistent configuration instead of at the first fix.

## SWR-GPSH-015: Build: The rover_gps_heading shall keep its domain and application code (geo math, HeadingAlig... (Functional)
The rover_gps_heading shall keep its domain and application code (geo math, HeadingAlignmentEstimator, AlignHeadingUseCase) in the rover_gps_heading_core static library without ROS dependencies.
- Rationale: Clean Architecture: the alignment logic is unit-testable without a ROS graph.
