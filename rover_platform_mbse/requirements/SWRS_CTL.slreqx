# SWRS_CTL
rover_controller Software Requirements Specification (ROVER-A1-ROVER_CONTROLLER-SWRS-V-001). rover_controller is the configuration and launch composition of the Rover A1 ros2_control controllers. It starts controller_manager (ros2_control_node) on hardware, loads the robot description, and spawns rover_joint_state_broadcaster, rover_drive_controller (diff_drive_controller, skid-steer kinematics, velocity/acceleration limits, command time-out, wheel odometry) chained into four per-wheel velocity PID controllers (rover_controller/SeededPidController, a pid_controller subclass provided by this package), and rover_imu_broadcaster. It also ships drive-train tuning tools (wheel_step_response, wheel_odom_calibration).

## SWR-CTL-001: Performance: The rover_controller shall configure controller_manager with update_rate 100 Hz and run... (Functional)
The rover_controller shall configure controller_manager with update_rate 100 Hz and run the four wheel PID controllers at that rate.
- Rationale: SYS-SR-002 requires a wheel velocity control loop of at least 50 Hz.

## SWR-CTL-002: Functional: The rover_controller shall chain rover_drive_controller (diff_drive_controller/DiffDriv... (Functional)
The rover_controller shall chain rover_drive_controller (diff_drive_controller/DiffDriveController) into one rover_controller/SeededPidController per wheel joint (fl, fr, rl, rr), each commanding that joint's velocity interface and closing the loop on its velocity state, with rl/fl as left wheels and rr/fr as right wheels.
- Rationale: SYS-SR-002/003: closed-loop wheel velocity control under skid-steer kinematics; diff_drive reads each PID's exported velocity state for odometry (open_loop false).

## SWR-CTL-003: Functional: The rover_controller shall provide SeededPidController, a pid_controller::PidController... (Functional)
The rover_controller shall provide SeededPidController, a pid_controller::PidController whose on_activate() copies each finite claimed hardware state value into the matching exported state interface, leaving NaN where the hardware has no value yet and skipping any pair whose names do not line up.
- Rationale: The stock PidController exports NaN until its first update; the chained diff_drive then reads NaN on its first cycle and controller_manager deactivates the whole drive chain on every activation on the real rover.

## SWR-CTL-004: Parameter: The rover_controller shall configure every wheel PID with p 0.05, i 1.0, d 0.04, feedfo... (Functional)
The rover_controller shall configure every wheel PID with p 0.05, i 1.0, d 0.04, feedforward_gain 1.0, u_clamp +/-12.58 rad/s, back_calculation anti-windup, save_i_term false, and i_clamp +/-0.25 on fl/fr and +/-0.33 on rl/rr.
- Rationale: Feed-forward carries the open-loop rad/s-scaled duty; the integral trims load/battery/slip error. save_i_term false clears the integral on each (re)activation (e.g. after an E-Stop) so no stale I-term carries into the next drive.

## SWR-CTL-005: Parameter: The rover_controller shall configure rover_drive_controller with wheel_separation 0.617... (Functional)
The rover_controller shall configure rover_drive_controller with wheel_separation 0.617 m, wheel_radius 0.1651 m, wheels_per_side 2, wheel_separation_multiplier 1.659, left/right wheel_radius_multiplier 1.0 and update_rate 50 Hz.
- Rationale: SYS-SR-003 skid-steer kinematics. The separation multiplier is the empirical skid-steer correction (effective track 0.617 x 1.659 = 1.0236 m), not geometry.

## SWR-CTL-006: Interface: The rover_controller shall make rover_drive_controller subscribe to cmd_vel and publish... (Functional)
The rover_controller shall make rover_drive_controller subscribe to cmd_vel and publish nav_msgs/Odometry on odometry/wheels every drive update (50 Hz) with odom_frame_id odom, base_frame_id base_footprint, twist covariance diagonal [5.4e-5, 5.4e-5, 0, 0, 0, 1.9e-4] and enable_odom_tf false.
- Rationale: SYS-SR-003 requires wheel odometry; SYS-SR-021 REP-105 frames. The odom->base_footprint TF is left to the EKF, so the controller must not also publish it.

## SWR-CTL-007: Performance: The rover_controller shall produce wheel odometry whose travelled-distance error is <= ... (Functional)
The rover_controller shall produce wheel odometry whose travelled-distance error is <= 5 % [TBC per SYS-SR-003] when the rover drives 10 m straight at 0.5 m/s on flat ground.
- Rationale: SYS-SR-003 acceptance. Accuracy depends on the calibrated radius and separation multipliers.

## SWR-CTL-008: Safety: The rover_controller shall limit rover_drive_controller body velocity to linear.x withi... (Functional)
The rover_controller shall limit rover_drive_controller body velocity to linear.x within [-0.95, 0.95] m/s and angular.z within [-1.5, 1.5] rad/s for every command received on cmd_vel.
- Rationale: SYS-SR-004 caps linear velocity at 1.0 m/s and angular velocity at 1.7 rad/s for commands from any source; all sources reach the wheels only through this controller.

## SWR-CTL-009: Performance: The rover_controller shall limit rover_drive_controller linear acceleration and deceler... (Functional)
The rover_controller shall limit rover_drive_controller linear acceleration and deceleration to 2.7 m/s^2 and angular acceleration and deceleration to 3.74 rad/s^2 in both directions.
- Rationale: SYS-SR-013 requires linear and angular acceleration limits.

## SWR-CTL-010: Safety: The rover_controller shall configure rover_drive_controller with cmd_vel_timeout 0.5 s ... (Functional)
The rover_controller shall configure rover_drive_controller with cmd_vel_timeout 0.5 s so that the wheel references are set to zero when no velocity command has been received for 0.5 s.
- Rationale: SYS-SR-011 requires the rover to stop if no valid velocity command is received within 500 ms.

## SWR-CTL-011: Safety: The rover_controller shall keep the outer-wheel reference at full linear plus full angu... (Functional)
The rover_controller shall keep the outer-wheel reference at full linear plus full angular command, plus the wheel PID i_clamp_max, at or below the URDF wheel joint velocity limit (10.958 rad/s).
- Rationale: diff_drive limits linear.x and angular.z independently; the wheel PIDs add up to i_clamp_max on top of the feed-forward reference. Staying below the joint limit keeps the drive inside the modelled motor capability.

## SWR-CTL-012: Build: The rover_controller shall keep wheel_radius and wheel_separation in config/wheel_01_co... (Functional)
The rover_controller shall keep wheel_radius and wheel_separation in config/wheel_01_controller.yaml equal to rover_description/config/wheel_01.yaml and fail its test suite otherwise.
- Rationale: rover_description/config/wheel_01.yaml is the single source of truth for wheel geometry; drift would corrupt odometry (SYS-SR-003).

## SWR-CTL-013: Interface: The rover_controller shall run rover_joint_state_broadcaster (joint_state_broadcaster) ... (Functional)
The rover_controller shall run rover_joint_state_broadcaster (joint_state_broadcaster) at update_rate 20 Hz, publishing sensor_msgs/JointState on joint_states for the four wheel joints.
- Rationale: Wheel joint states feed robot_state_publisher /tf (SYS-SR-021); 20 Hz matches the encoder rate and limits Zenoh traffic.

## SWR-CTL-014: Interface: The rover_controller shall run rover_imu_broadcaster (imu_sensor_broadcaster) publishin... (Functional)
The rover_controller shall run rover_imu_broadcaster (imu_sensor_broadcaster) publishing sensor_msgs/Imu on imu/data with frame_id <namespace>/imu_link from sensor <namespace>/imu, with static diagonal covariances 1.8e-3 (orientation), 1.0e-4 (angular velocity) and 7.6e-4 (linear acceleration).
- Rationale: SYS-SR-019 requires IMU orientation, angular velocity and linear acceleration with valid covariance fields.

## SWR-CTL-015: Performance: The rover_controller shall publish imu/data at 100 Hz or faster. (Functional)
The rover_controller shall publish imu/data at 100 Hz or faster.
- Rationale: SYS-SR-019 requires the IMU topic at >= 100 Hz. The IMU hardware samples at 125 Hz (data_interval_ms 8) and controller_manager runs at 100 Hz, but the broadcaster update_rate is 50 Hz to match the EKF rate.

## SWR-CTL-016: Build: The rover_controller shall give every controller an update_rate that divides the contro... (Functional)
The rover_controller shall give every controller an update_rate that divides the controller_manager update_rate evenly and does not exceed it.
- Rationale: Otherwise controller_manager runs the controller at an uneven period.

## SWR-CTL-017: Lifecycle: The rover_controller shall, in rover_controller.launch.py, activate rover_joint_state_b... (Functional)
The rover_controller shall, in rover_controller.launch.py, activate rover_joint_state_broadcaster, then rover_drive_controller together with its chained wheel PIDs in one --activate-as-group switch, then rover_imu_broadcaster, each only after the previous spawner exited with code 0, shut the launch down naming the controller and exit code when a spawner fails, and emit ControllersActive only after all three succeeded.
- Rationale: Deterministic bring-up: rover_bringup starts the rest of the stack on ControllersActive (SYS-SR-024 automatic start to Idle), and a half-started drive chain must not be left running.

## SWR-CTL-018: Performance: The rover_controller shall, in rover_controller.launch.py, start ros2_control_node with... (Functional)
The rover_controller shall, in rover_controller.launch.py, start ros2_control_node with --disable-rosout-logs and a single /diagnostics -> diagnostics remap, and apply controller topic remaps only through each controller's node_options_args.
- Rationale: /rosout publishes from update() stalled the 100 Hz loop for up to 4.2 s under rmw_zenoh, past the 500 ms motor watchdog; controllers ignore process-wide remaps (use_global_arguments false).

## SWR-CTL-019: Functional: The rover_controller shall, in rover_controller.launch.py, select the controller config... (Functional)
The rover_controller shall, in rover_controller.launch.py, select the controller configuration in the order explicit controller_config_path, then <common_dir_path>/rover_controller/config/<wheel_type>_controller.yaml, then the bundled config/<wheel_type>_controller.yaml, replace every "<namespace>/" placeholder with the namespace prefix, and pass the same resolved file to controller_manager, every spawner and the simulation robot description.
- Rationale: One resolved configuration for all consumers avoids hardware and simulation diverging.

## SWR-CTL-020: Safety: The rover_controller shall make its tuning tools (wheel_step_response, wheel_odom_calib... (Functional)
The rover_controller shall make its tuning tools (wheel_step_response, wheel_odom_calibration) publish velocity commands on the cmd_topic parameter (default: the twist_mux input teleop_foxglove_cmd_vel_stamped) and move the rover only when the parameter enable_motion is true (default false), printing the planned schedule otherwise.
- Rationale: Calibration drives are still subject to the twist_mux priority and E-Stop motion lock (SYS-SR-005) and must never move the rover by accident.
