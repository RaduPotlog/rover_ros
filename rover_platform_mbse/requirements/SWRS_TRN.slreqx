# SWRS_TRN
rover_transport Software Requirements Specification (ROVER-A1-ROVER_TRANSPORT-SWRS-V-001). rover_transport is the rover's byte-transport layer, a hard fork of ros-drivers/transport_drivers v1.2.0 laid out under Clean Architecture. It covers three sub-packages. rover_io_context holds the shared ports, the inbound/outbound byte bridges and the ASIO thread pool, with no ROS dependency. rover_udp_driver provides the lifecycle UdpReceiverNode and UdpSenderNode (UDP <-> udp_read/udp_write), which rover_battery uses for the BMS bridge on UDP port 4444, rover_crsf_teleop uses for the ELRS/CRSF receiver that the RUTX11 router forwards on UDP port 10111 (accepting datagrams from the router, 192.168.1.1, only), and rover_led uses for the two LED panel channels on UDP ports 3334 and 3333. rover_modbus_driver is a synchronous Modbus TCP discrete-I/O client library with no node, used in-process by rover_hardware_interface's RoverSafetyController for the PLC E-stop/GPIO coils. rover_asio_cmake_module only provides find_package(ASIO). The former rover_serial_driver (lifecycle SerialBridgeNode, UART <-> serial_read/serial_write) was removed in 2026-10 when its only consumer, the ELRS receiver, moved onto the RUTX11 router (rover_transport/README.md:14-17); its requirements SWR-TRN-001 to SWR-TRN-003 were deleted with it and their IDs are not reused. Two libraries outside the package support it. rover_modbus is a vendored, TCP-only fork of Mazurel/Modbus that supplies the Modbus_Core frame codec and the Modbus_Tcp sockets. rover_utils is not a build dependency of rover_transport; its Python launch helpers are used by the consumer launch files (for example rover_led). The package is responsible for moving raw bytes between devices and ROS 2 without interpreting them, except for Modbus framing. Protocol decoding belongs to the consumers.

## SWR-TRN-004: Lifecycle: The rover_transport shall implement UdpReceiverNode and UdpSenderNode as ROS 2 managed ... (Functional)
The rover_transport shall implement UdpReceiverNode and UdpSenderNode as ROS 2 managed lifecycle nodes. on_configure shall open the socket and return FAILURE if it cannot be opened. on_activate and on_deactivate shall enable and disable data transfer. on_cleanup and on_shutdown shall close the socket and release all publishers and subscriptions so the node can be configured again.
- Rationale: The transport owns hardware resources. Per project rules, resource owners are lifecycle-managed.

## SWR-TRN-005: Lifecycle: The rover_transport shall, when a transport nodes autostart parameter is true, trigger ... (Functional)
The rover_transport shall, when a transport node's autostart parameter is true, trigger configure and then activate once from the executor immediately after construction, without retrying if configure fails.
- Rationale: launch_ros' ComposableLifecycleNode autostart does not reach components in a namespaced container, so the nodes bring themselves up. This is needed for unattended start-up.

## SWR-TRN-006: Interface: The rover_transport shall, in UdpReceiverNode, bind a UDP/IPv4 socket to the configured... (Functional)
The rover_transport shall, in UdpReceiverNode, bind a UDP/IPv4 socket to the configured ip:port and publish every non-empty received datagram on udp_read as udp_msgs/UdpPacket with QoS depth 100, header.stamp set to the node clock at reception and header.frame_id set to the configured ip.
- Rationale: The BMS bridge sends battery data over UDP, which rover_battery decodes into the battery state. The RUTX11 router forwards the ELRS receiver's raw CRSF bytes over UDP, which rover_crsf_teleop decodes into RC commands.

## SWR-TRN-007: Functional: The rover_transport shall keep the UDP receiver armed after a successful zero-length da... (Functional)
The rover_transport shall keep the UDP receiver armed after a successful zero-length datagram, so that later datagrams are still published.
- Rationale: Upstream stopped receiving for good after a legal zero-length UDP packet. That would silently freeze the battery data.

## SWR-TRN-008: Functional: The rover_transport shall recover from a receive error on a UDP transport by re-arming ... (Functional)
The rover_transport shall recover from a receive error on a UDP transport by re-arming the receive, and resume publishing without operator action.
- Rationale: Today one receive error permanently stops the data stream while the node stays ACTIVE. The consumer then sees stale battery data or a lost RC teleop link with no fault reported.

## SWR-TRN-009: Interface: The rover_transport shall, in UdpSenderNode, subscribe to udp_write (udp_msgs/UdpPacket... (Functional)
The rover_transport shall, in UdpSenderNode, subscribe to udp_write (udp_msgs/UdpPacket, KeepLast(32), best effort) and transmit each message's data as one UDP datagram to the configured ip:port while the node is ACTIVE.
- Rationale: rover_led sends each LED panel's SK9822 frame to its LED board over UDP.

## SWR-TRN-010: Parameter: The rover_transport shall declare the UDP node parameters ip (string), port (int) and a... (Functional)
The rover_transport shall declare the UDP node parameters ip (string), port (int) and autostart (bool, default false), and shall fail the configure transition with a logged error when port is outside 1..65535 or the socket cannot be opened or bound.
- Rationale: Upstream defaulted port to 0 and never checked it.

## SWR-TRN-011: Safety: The rover_transport shall not write any byte to a UDP endpoint while the owning node is... (Functional)
The rover_transport shall not write any byte to a UDP endpoint while the owning node is not in the ACTIVE state, and shall count the bytes it discards this way.
- Rationale: A deactivated node must not drive hardware. This is the single most safety-relevant rule of the byte drivers, and it now lives in one testable place.

## SWR-TRN-012: Performance: The rover_transport shall use a 2048-byte receive buffer for each UDP socket, and shall... (Functional)
The rover_transport shall use a 2048-byte receive buffer for each UDP socket, and shall forward only the valid prefix of each read (never more bytes than were received or than the buffer holds).
- Rationale: Bounds memory per transport and prevents over-reads when converting to ROS messages.

## SWR-TRN-013: Lifecycle: The rover_transport shall make closing a UDP socket wait until no receive or send handl... (Functional)
The rover_transport shall make closing a UDP socket wait until no receive or send handler of that socket is running or queued, and shall drop received data without throwing once the ROS context is shut down or the publish fails.
- Rationale: Nodes must be torn down safely (cleanup, container unload, Ctrl-C) while data is still arriving, with no use-after-free or uncaught exception on the ASIO thread.

## SWR-TRN-014: Interface: The rover_transport shall register UdpReceiverNode and UdpSenderNode as rclcpp_componen... (Functional)
The rover_transport shall register UdpReceiverNode and UdpSenderNode as rclcpp_components, and shall let several transport nodes share one externally owned IoContext thread pool.
- Rationale: Consumers load the transports into their own container with intra-process communication, so high-rate byte traffic (LED frames, CRSF datagrams) does not cross the Zenoh router.

## SWR-TRN-015: Interface: The rover_transport shall provide, in rover_modbus_driver, an in-process synchronous Mo... (Functional)
The rover_transport shall provide, in rover_modbus_driver, an in-process synchronous Modbus TCP discrete-I/O client (DiscreteIoPort) that reads discrete inputs (FC2), reads coils (FC1, single or a batched range returning exactly count values) and writes a single coil (FC5), addressed to unit id 255.
- Rationale: RoverSafetyController reads and writes the PLC's E-stop and GPIO coils in-process on the safety path. A topic round-trip would add latency and a new failure mode.

## SWR-TRN-016: Safety: The rover_transport shall refuse a coil write whose CoilInfo.is_coil_engage_allowed is ... (Functional)
The rover_transport shall refuse a coil write whose CoilInfo.is_coil_engage_allowed is false: no Modbus frame is sent, an error is logged, and this holds even when the link is down.
- Rationale: Guards read-only safety coils against accidental writes from the controller.

## SWR-TRN-017: Functional: The rover_transport shall establish the initial Modbus TCP connection with up to connec... (Functional)
The rover_transport shall establish the initial Modbus TCP connection with up to connection_retry_count attempts (0 = retry forever), waiting connection_retry_delay_ms between them, and shall throw std::invalid_argument for an empty host and std::runtime_error once the attempts are exhausted.
- Rationale: The safety controller cannot run without the PLC link. Configuration must either wait for it or fail cleanly.

## SWR-TRN-018: Functional: The rover_transport shall, after any failed Modbus transaction, drop the TCP link, then... (Functional)
The rover_transport shall, after any failed Modbus transaction, drop the TCP link, then fail operations fast with std::runtime_error inside a reconnection backoff window and re-dial lazily on the first operation after it. The window starts at connection_retry_delay_ms (minimum 1 ms) and doubles on each failure up to 30 s. The backoff resets when a re-dial succeeds.
- Rationale: A post-configure link drop used to be permanent and could take the process down. Lazy, backed-off reconnection limits how long a blocking dial can stall the safety controller.

## SWR-TRN-019: Performance: The rover_transport shall abort a Modbus transaction whose reply does not arrive within... (Functional)
The rover_transport shall abort a Modbus transaction whose reply does not arrive within ClientSettings.response_timeout_ms, which defaults to 500 ms and is configurable by the caller.
- Rationale: Bounds how long one stalled read or write can hold the safety link and delay the PLC watchdog heartbeat and E-stop state reporting.

## SWR-TRN-020: Performance: The rover_transport shall bound every Modbus TCP connection attempt, initial or re-dial... (Functional)
The rover_transport shall bound every Modbus TCP connection attempt, initial or re-dial, by a configurable connect timeout of [TBD per SYS-SR-023] ms, so that dialling a black-holed PLC host cannot block the caller for the kernel SYN-retry period.
- Rationale: MB::TCP::Connection::with() performs a blocking ::connect() with no timeout. A re-dial inside the ros2_control safety path can then stall it for many seconds.

## SWR-TRN-021: Diagnostics: The rover_transport shall publish diagnostic status on /diagnostics at 1 Hz or faster f... (Functional)
The rover_transport shall publish diagnostic status on /diagnostics at 1 Hz or faster for each UDP transport node (endpoint open/closed, bytes forwarded, bytes dropped while inactive, datagrams rejected by the source filter, last receive error) and for the Modbus link (connected/disconnected, current backoff), reporting ERROR when a transport has closed or the link is down.
- Rationale: A closed socket, a stalled UDP receiver, a flood of rejected foreign datagrams or a dropped PLC link is currently only visible as log lines. The system requires sensor and E-stop-circuit health on /diagnostics.

## SWR-TRN-022: Build: The rover_transport shall build as ament_cmake packages on the rovers ROS 2 distributio... (Functional)
The rover_transport shall build as ament_cmake packages on the rover's ROS 2 distribution (lyrical, [TBD per SYS-SR-020]), keeping rover_io_context free of any ROS dependency and keeping MB:: frame types and sockets out of rover_modbus_driver's domain and application layers, enforced by the core_purity_check test.
- Rationale: Upstream transport_drivers has no lyrical release, so the rover builds its fork. The layering keeps protocol logic testable without ROS or sockets.

## SWR-TRN-023: Safety: The rover_transport shall, in UdpReceiverNode, accept a source_ip parameter (string, de... (Functional)
The rover_transport shall, in UdpReceiverNode, accept a source_ip parameter (string, default empty = any source) and, when it is set, drop inside the socket every datagram whose sender address differs from source_ip before it is published on udp_read, count the dropped datagrams (rejectedDatagrams()), log them at the 1st, 2nd, 4th, 8th, ... rejection, keep receiving afterwards, warn at configure when source_ip is empty, and fail the configure transition when source_ip does not parse as an IPv4 address. The receiver shall record each datagram's sender in an endpoint separate from the bound one, so that receiving never overwrites the bound address.
- Rationale: A consumer whose input can move the rover must be able to accept only its known sender. UdpPacket.address carries the bound address, not the sender, so the filter cannot be applied downstream. Upstream received into the bound endpoint, so the first datagram replaced the bound address with the sender's.
