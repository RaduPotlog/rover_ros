# SWRS_MUX
rover_twist_mux Software Requirements Specification (ROVER-A1-ROVER_TWIST_MUX-SWRS-V-001). rover_twist_mux arbitrates the rover's velocity command sources. It configures and launches the upstream twist_mux node (the sole publisher of cmd_vel) with four prioritised, time-limited TwistStamped inputs (ELRS RC, Foxglove joystick, Driver UI, Nav 2) and one safety lock, and it provides two adapters: rover_motion_lock_node, which maps the safety PLC state (hardware_interface/safety_status + safety_command_echo) onto the fail-safe-closed motion_lock (std_msgs/Bool) that masks every input, and rover_command_freshness_node, which drops Driver UI commands delivered late by a stalled websocket. It is gate 2 of the five motion gates in rover_arch/SAFETY_CHAIN.md; the contactor and the hardware interface's write() gate are independent of it.

## SWR-MUX-001: Interface: The rover_twist_mux shall publish the arbitrated velocity command as geometry_msgs/Twis... (Functional)
The rover_twist_mux shall publish the arbitrated velocity command as geometry_msgs/TwistStamped on cmd_vel (twist_mux cmd_vel_out remapped) and shall be the only publisher of cmd_vel in the platform launch.
- Rationale: A single arbiter prevents sources racing each other on cmd_vel; the drive controller consumes only this topic.

## SWR-MUX-002: Functional: The rover_twist_mux shall accept velocity commands from four inputs with strictly order... (Functional)
The rover_twist_mux shall accept velocity commands from four inputs with strictly ordered priorities - cmd_elrs (teleop_elrs_cmd_vel_stamped, 110) > joystick (teleop_foxglove_cmd_vel_stamped, 100) > driver_interface (teleop_driver_interface_cmd_vel_fresh_stamped, 8) > nav (nav_cmd_vel_stamped, 5) - and shall forward only the highest-priority input that has not timed out.
- Rationale: The line-of-sight RC operator has the last word; every teleop source pre-empts autonomy deterministically.

## SWR-MUX-003: Safety: The rover_twist_mux shall stop forwarding an input when no message has been received on... (Functional)
The rover_twist_mux shall stop forwarding an input when no message has been received on it within its timeout: 0.5 s for cmd_elrs, joystick and nav, and 0.3 s for driver_interface.
- Rationale: A silent or dead source must not keep the rover moving on its last command; the Driver UI timeout is three periods of its 10 Hz stream.

## SWR-MUX-004: Safety: The rover_twist_mux shall mask every velocity input while motion_lock is true or has no... (Functional)
The rover_twist_mux shall mask every velocity input while motion_lock is true or has not been received within 0.5 s, by configuring the motion_lock lock at priority 200, above every input priority.
- Rationale: An active E-Stop condition must stop all sources, and a dead lock publisher must close the mux rather than open it.

## SWR-MUX-005: Interface: The rover_twist_mux shall publish the motion lock state as std_msgs/Bool on motion_lock... (Functional)
The rover_twist_mux shall publish the motion lock state as std_msgs/Bool on motion_lock with QoS KeepLast(1), reliable, at publish_frequency (10.0 Hz).
- Rationale: twist_mux treats a lock topic older than its 0.5 s timeout as locked, so the publisher must stay well inside that window.

## SWR-MUX-006: Interface: The rover_twist_mux shall subscribe hardware_interface/safety_status (rover_msgs/Safety... (Functional)
The rover_twist_mux shall subscribe hardware_interface/safety_status (rover_msgs/SafetyStatus) and hardware_interface/safety_command_echo (rover_msgs/SafetyCommandEcho) with QoS KeepLast(1), reliable, volatile, and shall use SafetyCommandEcho fields only as reasons to inhibit motion.
- Rationale: Matches the hardware interface publishers; a latched (transient-local) sample would hide a dead publisher. Echoes of commanded coils are never evidence of plant state.

## SWR-MUX-007: Safety: The rover_twist_mux shall assert motion_lock (true) from start-up until both a SafetySt... (Functional)
The rover_twist_mux shall assert motion_lock (true) from start-up until both a SafetyStatus and a SafetyCommandEcho message have been received.
- Rationale: Fail-safe closed: with no safety IO there is no driving; acting on one half alone would read the missing half's stop conditions as inactive.

## SWR-MUX-008: Safety: The rover_twist_mux shall assert motion_lock when the older of the two safety messages ... (Functional)
The rover_twist_mux shall assert motion_lock when the older of the two safety messages is older than gpio_timeout (1.0 s).
- Rationale: A hardware interface that stops publishing must not leave the mux open on last-known values; neither topic may hide behind the other.

## SWR-MUX-009: Safety: The rover_twist_mux shall assert motion_lock while SafetyStatus.link_healthy is false, ... (Functional)
The rover_twist_mux shall assert motion_lock while SafetyStatus.link_healthy is false, even when no stop condition is active.
- Rationale: With the PLC link down the messages keep arriving with last-known-good values, so staleness alone cannot detect it.

## SWR-MUX-010: Safety: The rover_twist_mux shall assert motion_lock while any enabled stop condition is active... (Functional)
The rover_twist_mux shall assert motion_lock while any enabled stop condition is active - hardware E-Stop button pressed, software E-Stop user button triggered, motor-driver fault stop, or safety latch held - with all four conditions enabled in the shipped configuration.
- Rationale: Any single active stop is sufficient to inhibit; the latch condition keeps motion inhibited after the trip source clears until an explicit reset.

## SWR-MUX-011: Parameter: The rover_twist_mux shall treat an open motor contactor as a lock condition only when r... (Functional)
The rover_twist_mux shall treat an open motor contactor as a lock condition only when require_motor_contactor_engaged is true, which shall be false in the shipped configuration.
- Rationale: The contactor feedback has inverted sense and is unverified on hardware, so it is opt-in.

## SWR-MUX-012: Parameter: The rover_twist_mux shall reject a motion-lock publish_frequency outside [1.0, 100.0] H... (Functional)
The rover_twist_mux shall reject a motion-lock publish_frequency outside [1.0, 100.0] Hz and a gpio_timeout outside [0.1, 10.0] s.
- Rationale: Bounds keep the lock republished inside the mux lock timeout and keep the staleness window meaningful.

## SWR-MUX-013: Diagnostics: The rover_twist_mux shall report a Motion lock diagnostic (hardware ID Motion Lock) tha... (Functional)
The rover_twist_mux shall report a 'Motion lock' diagnostic (hardware ID 'Motion Lock') that is STALE before the first evaluation, ERROR when the safety input is missing, stale or the PLC link is unhealthy, WARN when a stop condition holds the lock, and OK when motion is permitted, including the per-flag values, topic ages and policy settings.
- Rationale: Operators need to see why the rover will not move; the diagnostic is derived from the same evaluation as the lock so they cannot disagree.

## SWR-MUX-014: Functional: The rover_twist_mux shall relay a Driver UI command from teleop_driver_interface_cmd_ve... (Functional)
The rover_twist_mux shall relay a Driver UI command from teleop_driver_interface_cmd_vel_stamped to teleop_driver_interface_cmd_vel_fresh_stamped unchanged only if its receive-time-minus-stamp latency exceeds the latency baseline by at most max_delay (0.3 s), and shall drop commands with a zero or negative header stamp.
- Rationale: twist_mux judges freshness by arrival time; a websocket that stalls on Wi-Fi delivers old commands in a burst, which would replay seconds-old motion.

## SWR-MUX-015: Functional: The rover_twist_mux shall, in rover_command_freshness_node, let the filters latency bas... (Functional)
The rover_twist_mux shall, in rover_command_freshness_node, let the filter's latency baseline rise by at most max_clock_drift (0.001 s per s of traffic, crediting at most 1.0 s per command gap), and shall re-baseline only on a run of rejected commands that starts after at least resync_gap (1.0 s) of silence and stays within max_delay of itself for resync_time (2.0 s).
- Rationale: Follows clock drift between browser and rover and recovers from a backwards clock step, while a growing mid-stream backlog or a stale burst can never re-baseline itself.

## SWR-MUX-016: Interface: The rover_twist_mux shall, in rover_command_freshness_node, subscribe and publish geome... (Functional)
The rover_twist_mux shall, in rover_command_freshness_node, subscribe and publish geometry_msgs/TwistStamped with QoS KeepLast(10), reliable.
- Rationale: Matches foxglove_bridge's reliable client publisher and twist_mux's SystemDefaults subscription; a best-effort hop would reintroduce the lost-zero risk.

## SWR-MUX-017: Parameter: The rover_twist_mux shall, in rover_command_freshness_node, treat the nodes parameters ... (Functional)
The rover_twist_mux shall, in rover_command_freshness_node, treat the node's parameters as read-only and reject max_delay outside [0.05, 5.0] s, max_clock_drift outside [0.0, 0.1], resync_time outside [0.5, 60.0] s and resync_gap outside [0.1, 60.0] s.
- Rationale: Prevents runtime changes to a safety-relevant filter and nonsensical settings.

## SWR-MUX-018: Diagnostics: The rover_twist_mux shall, in rover_command_freshness_node, report a Command freshness ... (Functional)
The rover_twist_mux shall, in rover_command_freshness_node, report a 'Command freshness' diagnostic (hardware ID 'Command Freshness') that is WARN for 5.0 s after any dropped command and OK otherwise, with accepted/dropped/resync counts, latency baseline, last excess delay and max_delay.
- Rationale: Makes a stalling Driver UI link visible on a 1 Hz dashboard, not only in the log.

## SWR-MUX-019: Safety: The rover_twist_mux shall publish motion_lock immediately when a received SafetyStatus ... (Functional)
The rover_twist_mux shall publish motion_lock immediately when a received SafetyStatus or SafetyCommandEcho changes the evaluated lock state, in addition to the periodic publication, so that the lock path contributes to the 100 ms software E-Stop budget.
- Rationale: Today the lock is re-evaluated only in the 10 Hz timer, so a stop condition can wait up to one timer period after it arrives (on top of the 20 Hz safety_status period) before the mux is closed.

## SWR-MUX-020: Interface: The rover_twist_mux shall publish which input is currently selected (or none, or locked... (Functional)
The rover_twist_mux shall publish which input is currently selected (or none, or locked) on a ROS topic whenever the selection changes, for use by the platform mode manager.
- Rationale: The SYS-SR-010 Teleoperation and Autonomous states can only be derived from which source currently commands the rover; no component exposes that today.
