# SWRS_HWI
rover_hardware_interface Software Requirements Specification (ROVER-A1-ROVER_HARDWARE_INTERFACE-SWRS-V-001). rover_hardware_interface provides the two ros2_control hardware plugins of Rover A1: RoverA1System (hardware_interface::SystemInterface) drives the four wheel joints through four Phidget DCC1000 DC motor controllers and talks Modbus TCP to the safety PLC (E-Stop latch, CPU watchdog heartbeat, contactor feedback, general-purpose aux IO); PhidgetImuSensor (hardware_interface::SensorInterface) reads the Phidgets Spatial MOT0110 IMU through a Madgwick filter. RoverA1System also runs the rover_hardware_controller helper node inside the controller_manager process, which publishes the safety, aux IO and driver state topics, serves the software E-Stop / latch reset / aux output services and reports /diagnostics. It is responsible for gating motor commands on the E-Stop state and on latched hardware faults; the contactor opening in hardware remains the primary stop.

## SWR-HWI-001: Interface: The rover_hardware_interface shall export the pluginlib class rover_hardware_interface/... (Functional)
The rover_hardware_interface shall export the pluginlib class rover_hardware_interface/RoverA1System (hardware_interface::SystemInterface) that exposes, for each of exactly four wheel joints matched by the name sequences fl, fr, rl and rr, one velocity command interface and the state interfaces position, velocity and effort in that order, and fail on_init() with ERROR when the joint count, joint names or interface list differ.
- Rationale: SYS-SR-002 requires 4 wheel drive joints in velocity mode with encoder feedback; SYS-SR-020 requires ros2_control for the drive hardware interface. Rejecting a mismatching URDF at on_init() prevents a silently mis-wired drive.

## SWR-HWI-002: Functional: The rover_hardware_interface shall convert wheel velocity commands from rad/s at the wh... (Functional)
The rover_hardware_interface shall convert wheel velocity commands from rad/s at the wheel to a DCC1000 duty cycle using gear_ratio and max_rpm_motor_speed and clamp the result to [-1.0, 1.0], and report wheel position in rad, velocity in rad/s and effort in N·m derived from encoder_resolution, gear_ratio, motor_torque_constant and gearbox_efficiency.
- Rationale: REP-103 SI units on the ros2_control interfaces (SYS-SR-021) and correct velocity-mode actuation with encoder feedback (SYS-SR-002).

## SWR-HWI-003: Parameter: The rover_hardware_interface shall configure each DCC1000 with the URDF motor_accelerat... (Functional)
The rover_hardware_interface shall configure each DCC1000 with the URDF motor_acceleration (4.0 duty/s) and motor_current_limit (15.0 A) and fail on_init() when motor_acceleration is outside [0.5, 10000] duty/s, motor_current_limit outside [2, 25] A, motor_supply_voltage outside [8, 30] V or the derived current regulator gain outside [1, 100].
- Rationale: The current limit protects motor, DCC1000 and gearbox; rejecting out-of-range values at on_init() avoids a late SDK failure after the drive is energised.

## SWR-HWI-004: Lifecycle: The rover_hardware_interface shall, in on_configure(), start the safety controller befo... (Functional)
The rover_hardware_interface shall, in on_configure(), start the safety controller before initialising the motor drivers (up to max_rover_driver_initialization_attempts = 3), arm each DCC1000 hardware failsafe and zero all velocity commands in on_activate() (up to max_rover_driver_activation_attempts = 3), and zero all velocity commands in on_deactivate().
- Rationale: No stale command may be the first thing written to the drivers after a (re)activation, and the start-up E-Stop triggers must be released before the drivers are armed.

## SWR-HWI-005: Safety: The rover_hardware_interface shall, in every write() cycle, forward the controller velo... (Functional)
The rover_hardware_interface shall, in every write() cycle, forward the controller velocity commands to the drivers only when the component is ACTIVE, neither the software E-Stop nor the PLC latch is active and no hardware fault (motor failsafe trip or welded contactor) is latched, and otherwise discard the pending command and send zero velocity to all four drivers while ACTIVE or INACTIVE.
- Rationale: Defense in depth behind the contactor (SAFETY_CHAIN.md §5 gate 3). Zeros are sent rather than nothing so that the DCC1000 failsafe keeps being fed, and a stale command is never replayed after the latch clears.

## SWR-HWI-006: Interface: The rover_hardware_interface shall provide the service hardware_interface/sw_user_e_sto... (Functional)
The rover_hardware_interface shall provide the service hardware_interface/sw_user_e_stop_set (std_srvs/Trigger) that writes the sw_e_stop_user_button coil (COIL_2) true on the Modbus link with priority over IO polling, returning success=false with the error text when the write fails.
- Rationale: SYS-SR-007 requires a software E-Stop triggerable through the ROS interface. A service (not a latched topic) gives an acknowledgement and is never replayed to a late joiner (SAFETY_CHAIN.md §4).

## SWR-HWI-007: Performance: The rover_hardware_interface shall command zero velocity to all four drive joints withi... (Functional)
The rover_hardware_interface shall command zero velocity to all four drive joints within 100 ms of a hardware_interface/sw_user_e_stop_set request being received.
- Rationale: SYS-SR-007 latency budget. Today write() only inhibits once the software E-Stop is read back from the PLC through the IO poll cache, so the latency is the priority Modbus write (bounded by modbus_response_timeout_ms 150 ms plus one in-flight transaction) plus up to one safety_io_poll_period_ms (100 ms) plus a 10 ms control cycle.

## SWR-HWI-008: Safety: The rover_hardware_interface shall refuse hardware_interface/sw_user_e_stop_reset (succ... (Functional)
The rover_hardware_interface shall refuse hardware_interface/sw_user_e_stop_reset (success=false) unless the component is ACTIVE, every wheel velocity command is finite and within velocity_command_zero_tolerance (0.4 rad/s) of zero and every measured wheel velocity is finite and within velocity_state_zero_tolerance (0.05 rad/s) of zero.
- Rationale: SYS-SR-008: releasing the stop must not resume motion by itself; the rover may not be re-energised while commanded to move or still rolling (SAFETY_CHAIN.md §5 reset invariant).

## SWR-HWI-009: Safety: The rover_hardware_interface shall provide hardware_interface/sw_e_stop_latch_reset (st... (Functional)
The rover_hardware_interface shall provide hardware_interface/sw_e_stop_latch_reset (std_srvs/Trigger) that, only while ACTIVE, pulses the latch-reset coil (COIL_4) true for safety_latch_reset_pulse_ms (100 ms) and then false, clears the latched error-filter state and the welded-contactor fault, and re-arms the DCC1000 failsafe.
- Rationale: SYS-SR-008 requires an explicit operator reset after any E-Stop. The pulse must be wide enough for the relay input filter; a single call acknowledges all latched faults, which re-latch on the next read() if still present.

## SWR-HWI-010: Safety: The rover_hardware_interface shall refuse hardware_interface/sw_e_stop_latch_reset (suc... (Functional)
The rover_hardware_interface shall refuse hardware_interface/sw_e_stop_latch_reset (success=false) while any wheel velocity command exceeds velocity_command_zero_tolerance or any measured wheel velocity exceeds velocity_state_zero_tolerance.
- Rationale: SAFETY_CHAIN.md §5 states that the latch cannot be cleared while the rover is being commanded to move or while the wheels are still turning; SYS-SR-008 requires that reset does not by itself resume motion with non-zero commands present. After a hardware E-Stop the SW user-button reset (which has the check) is not needed, so the latch reset is the only reset and has no velocity check.

## SWR-HWI-011: Safety: The rover_hardware_interface shall, on every safety-controller start, drive the heartbe... (Functional)
The rover_hardware_interface shall, on every safety-controller start, drive the heartbeat, sw_e_stop_user_button and sw_e_stop_motor_driver_fault coils to true and the latch-reset and aux output coils to false, then release only the two software E-Stop inputs, so that the PLC latch stays asserted until an explicit hardware_interface/sw_e_stop_latch_reset.
- Rationale: SYS-SR-008: a (re)start of the software must never clear a stop by itself. The set-dominant latch set at start holds until the operator resets it.

## SWR-HWI-012: Safety: The rover_hardware_interface shall toggle the CPU watchdog heartbeat coil (COIL_1) ever... (Functional)
The rover_hardware_interface shall toggle the CPU watchdog heartbeat coil (COIL_1) every safety_wdg_kick_period_ms (200 ms) on a dedicated thread with absolute steady_clock deadlines and priority access to the Modbus link, counting late kicks and failed kicks without stopping the thread.
- Rationale: The safety relay latches the E-Stop if the heartbeat stops changing for its ~1 s window (SAFETY_CHAIN.md §3). The heartbeat is the hardware backstop for a dead CPU / process (SYS-SR-006 stop independent of software).

## SWR-HWI-013: Interface: The rover_hardware_interface shall connect by Modbus TCP to the safety PLC at modbus_ho... (Functional)
The rover_hardware_interface shall connect by Modbus TCP to the safety PLC at modbus_host:modbus_port (192.168.88.11:502) with a per-transaction response timeout of modbus_response_timeout_ms (150 ms), and refresh the cached safety and aux IO every safety_io_poll_period_ms (100 ms) using exactly four read transactions (one FC2, three FC1 blocks of at most 8 coils each within one PLC memory area).
- Rationale: SYS-SR-023 needs the E-Stop state in software; the block layout works around two measured Portenta Modbus server quirks (SAFETY_CHAIN.md §2) and bounds how long the poll can hold the link.

## SWR-HWI-014: Interface: The rover_hardware_interface shall publish rover_msgs/SafetyStatus on hardware_interfac... (Functional)
The rover_hardware_interface shall publish rover_msgs/SafetyStatus on hardware_interface/safety_status and rover_msgs/SafetyCommandEcho on hardware_interface/safety_command_echo at driver_states_update_frequency (20 Hz) with QoS reliable, volatile, KeepLast(1), routing HW E-Stop button, contactor feedback and latch status to SafetyStatus and the read-backs of software-driven coils to SafetyCommandEcho.
- Rationale: SYS-SR-023 requires the HW and SW E-Stop state on a ROS topic. Volatile (not transient_local) so that a late joiner cannot mistake a stale latched sample for a live publisher.

## SWR-HWI-015: Safety: The rover_hardware_interface shall set SafetyStatus.link_healthy and AuxIoState.link_he... (Functional)
The rover_hardware_interface shall set SafetyStatus.link_healthy and AuxIoState.link_healthy false unless both safety-controller threads are running and the last successful IO poll is at most 500 ms old, and stamp io_sample_time with the time of that poll.
- Rationale: Without it a dead PLC link is indistinguishable from a quiet one because the messages keep flowing with last-known-good values (SAFETY_CHAIN.md §4); rover_twist_mux locks motion on link_healthy false.

## SWR-HWI-016: Performance: The rover_hardware_interface shall publish a change of the hardware E-Stop button, soft... (Functional)
The rover_hardware_interface shall publish a change of the hardware E-Stop button, software E-Stop coil or PLC latch state on hardware_interface/safety_status or hardware_interface/safety_command_echo within 100 ms of the change at the PLC.
- Rationale: SYS-SR-023 latency budget. Today the path is up to one IO poll period (100 ms) plus four Modbus transactions plus up to one publish period at 20 Hz (50 ms).

## SWR-HWI-017: Diagnostics: The rover_hardware_interface shall populate SafetyStatus.latch_cause with the trip sour... (Functional)
The rover_hardware_interface shall populate SafetyStatus.latch_cause with the trip source that set the PLC latch (SW user button, SW motor-driver fault, CPU watchdog or HW user button).
- Rationale: Operators and SYS-SR-022 diagnostics need to know why the rover stopped; today the PLC exposes one latch bit and four SET sources (SAFETY_CHAIN.md §6).

## SWR-HWI-018: Safety: The rover_hardware_interface shall assert the sw_e_stop_motor_driver_fault coil (COIL_3... (Functional)
The rover_hardware_interface shall assert the sw_e_stop_motor_driver_fault coil (COIL_3) when a motor-driver fault (latched MOTOR_FAILSAFE_TRIPPED or FAULT_FLAG error) is detected, so that the PLC latch opens the contactor.
- Rationale: SAFETY_CHAIN.md §1 lists the SW motor-driver fault as one of the four SET sources of the latch; a driver fault should remove drive power through the hardware chain, not only through write() zero commands.

## SWR-HWI-019: Safety: The rover_hardware_interface shall latch a welded-contactor fault and inhibit motion wh... (Functional)
The rover_hardware_interface shall latch a welded-contactor fault and inhibit motion when the PLC latch is active and the motor contactor auxiliary contact still reports engaged for at least 500 ms, keeping the fault latched until hardware_interface/sw_e_stop_latch_reset.
- Rationale: Software half of the EDM loop: detects a stop that was commanded but did not remove drive power (SYS-SR-006).

## SWR-HWI-020: Safety: The rover_hardware_interface shall arm each DCC1000 hardware failsafe with motor_failsa... (Functional)
The rover_hardware_interface shall arm each DCC1000 hardware failsafe with motor_failsafe_timeout_ms (500 ms), keep feeding it with zero commands while motion is inhibited, and latch a MOTOR_FAILSAFE_TRIPPED error on the first trip that inhibits motion until hardware_interface/sw_e_stop_latch_reset.
- Rationale: Backstop for a stalled control loop: the motors brake when commands stop reaching the drivers, independently of the software E-Stop (supports SYS-SR-011 stop on loss of commands).

## SWR-HWI-021: Diagnostics: The rover_hardware_interface shall publish rover_msgs/RoverDriverState on hardware_inte... (Functional)
The rover_hardware_interface shall publish rover_msgs/RoverDriverState on hardware_interface/driver_state at driver_states_update_frequency (20 Hz) with QoS reliable, volatile, KeepLast(5), reporting per driver current, temperature, fault flags, data time-outs and comm_error, where comm_error is set when no Phidget telemetry callback arrived within driver_comm_timeout_ms (300 ms).
- Rationale: Drive-motor health for operators and rover_safety (SYS-SR-022).

## SWR-HWI-022: Diagnostics: The rover_hardware_interface shall publish on diagnostics, with hardware id Rover Syste... (Functional)
The rover_hardware_interface shall publish on diagnostics, with hardware id "Rover System", the tasks "system errors", "system status" and "safety plc link" at the diagnostic_updater period (default 1.0 s), reporting ERROR for any latched driver or error-filter fault, a stopped safety thread or a latched welded-contactor fault, and WARN for a late heartbeat or a contactor that is open while the latch is clear.
- Rationale: SYS-SR-022 requires drive-motor and E-Stop-circuit diagnostics at >= 1 Hz with induced faults reported as ERROR.

## SWR-HWI-023: Diagnostics: The rover_hardware_interface shall report the safety plc link diagnostic as ERROR when ... (Functional)
The rover_hardware_interface shall report the "safety plc link" diagnostic as ERROR when the last successful IO poll is older than 500 ms or when IO polls keep failing, even while both safety threads are running.
- Rationale: SYS-SR-022: a dead Modbus link with live threads is a fault of the E-Stop circuit telemetry and must appear as ERROR, consistent with link_healthy on the safety_status topic.

## SWR-HWI-024: Lifecycle: The rover_hardware_interface shall, in on_error(), assert the software E-Stop, broadcas... (Functional)
The rover_hardware_interface shall, in on_error(), assert the software E-Stop, broadcast an ERROR status on all diagnostic tasks and tear down the safety controller, drivers and ROS helper node.
- Rationale: A failed lifecycle transition must leave the rover stopped and visibly faulted (SYS-SR-008, SYS-SR-022).

## SWR-HWI-025: Interface: The rover_hardware_interface shall provide hardware_interface/aux_output_<0..5>/set (st... (Functional)
The rover_hardware_interface shall provide hardware_interface/aux_output_<0..5>/set (std_srvs/SetBool) that write PLC coils 8..13 without priority on the Modbus link, publish rover_msgs/AuxIoState on hardware_interface/aux_io_state at 20 Hz with QoS reliable, volatile, KeepLast(1), and drive all aux outputs off on every safety-controller start.
- Rationale: General-purpose IO shares the safety link but must never delay the heartbeat or an E-Stop write and never gate motion (SAFETY_CHAIN.md §2).

## SWR-HWI-026: Interface: The rover_hardware_interface shall export the pluginlib class rover_hardware_interface/... (Functional)
The rover_hardware_interface shall export the pluginlib class rover_hardware_interface/PhidgetImuSensor (hardware_interface::SensorInterface) that samples the Phidgets Spatial at data_interval_ms (8 ms, 125 Hz), fuses it with a Madgwick filter in the configured world_frame (enu) with use_mag false, exports 10 state interfaces (orientation x/y/z/w, angular_velocity x/y/z, linear_acceleration x/y/z) and returns ERROR from read() while the device is detached.
- Rationale: SYS-SR-019 requires an IMU providing orientation, angular velocity and linear acceleration at >= 100 Hz; the sensor itself samples at 125 Hz.

## SWR-HWI-027: Diagnostics: The rover_hardware_interface shall publish an IMU diagnostic status on diagnostics at >... (Functional)
The rover_hardware_interface shall publish an IMU diagnostic status on diagnostics at >= 1 Hz that reports ERROR while the Phidgets Spatial is detached or delivers no valid samples.
- Rationale: SYS-SR-022 requires sensor diagnostics; PhidgetImuSensor has no diagnostic_updater, so an IMU fault is visible only as a read() ERROR that deactivates the broadcaster.

## SWR-HWI-028: Build: The rover_hardware_interface shall keep domain and application code free of ROS, hardwa... (Functional)
The rover_hardware_interface shall keep domain and application code free of ROS, hardware_interface and vendor SDK includes and keep read()/write() free of blocking Modbus or Phidget SDK calls, enforced by the CTest checks domain_purity_check, application_purity_check and rt_path_purity_check.
- Rationale: Clean Architecture layering and a real-time-safe control path; the safety IO is served to read() from a cache under try_lock.
