# SWRS_LOC
rover_localization Software Requirements Specification (ROVER-A1-ROVER_LOCALIZATION-SWRS-V-001). rover_localization is a configuration-and-launch package (no own source code) that runs robot_localization filters for the rover. In the default mode it starts rover_ekf_node, which fuses wheel-odometry body velocities and IMU yaw rate into the continuous odom -> base_footprint estimate. With GPS fusion enabled (ROVER_USE_GPS) it also starts rover_ekf_global_node (map-frame filter adding GPS X/Y), rover_navsat_transform_node and rover_gps_heading_node (package rover_gps_heading). The GPS driver itself belongs to the sensor payload (rover_sensors, outside this boundary).

## SWR-LOC-001: Functional: The rover_localization shall run a robot_localization EKF node named rover_ekf_node whe... (Functional)
The rover_localization shall run a robot_localization EKF node named rover_ekf_node whenever the launch argument use_ekf is true.
- Rationale: A fused odometry estimate is needed by navigation and control above the wheel odometry of SYS-SR-003.

## SWR-LOC-002: Performance: The rover_localization shall configure rover_ekf_node to run at 50.0 Hz in 2D mode (two... (Functional)
The rover_localization shall configure rover_ekf_node to run at 50.0 Hz in 2D mode (two_d_mode true) with a sensor timeout of 0.1 s.
- Rationale: A 50 Hz fused estimate matches the drive control rate of SYS-SR-002 and gives local planners fresh odometry.

## SWR-LOC-003: Interface: The rover_localization shall fuse only the body linear velocities vx and vy from nav_ms... (Functional)
The rover_localization shall fuse only the body linear velocities vx and vy from nav_msgs/Odometry on odometry/wheels into rover_ekf_node, not the wheel-odometry pose.
- Rationale: Wheel-odometry X/Y is integrated along the drive controller's own (skid-biased) yaw and would conflict with the IMU heading; vy = 0 acts as a nonholonomic constraint.

## SWR-LOC-004: Interface: The rover_localization shall fuse only the yaw rate (vyaw) from sensor_msgs/Imu on imu/... (Functional)
The rover_localization shall fuse only the yaw rate (vyaw) from sensor_msgs/Imu on imu/data into rover_ekf_node, not the IMU absolute orientation or linear acceleration.
- Rationale: Absolute IMU orientation is magnetometer-influenced near the drive motors; the driver's linear acceleration includes gravity.

## SWR-LOC-005: Interface: The rover_localization shall publish the rover_ekf_node estimate as nav_msgs/Odometry o... (Functional)
The rover_localization shall publish the rover_ekf_node estimate as nav_msgs/Odometry on the relative topic odom (remapped from odometry/filtered).
- Rationale: odom is the fused odometry consumed by navigation, rover_gps_heading and the UI.

## SWR-LOC-006: Interface: The rover_localization shall make rover_ekf_node the only broadcaster of the odom -> ba... (Functional)
The rover_localization shall make rover_ekf_node the only broadcaster of the odom -> base_footprint transform, using world_frame odom, odom_frame odom, map_frame map and base_link_frame base_footprint, with the namespace as tf_prefix.
- Rationale: REP-105 requires a single continuous odom -> base chain; the drive controller's own odom TF is disabled so the EKF owns it.

## SWR-LOC-007: Interface: The rover_localization shall expose the robot_localization services of rover_ekf_node a... (Functional)
The rover_localization shall expose the robot_localization services of rover_ekf_node as localization/set_pose, localization/enable and localization/toggle.
- Rationale: Allows the operator or navigation to re-initialise and pause the filter.

## SWR-LOC-008: Diagnostics: The rover_localization shall enable print_diagnostics on every EKF and remap all locali... (Functional)
The rover_localization shall enable print_diagnostics on every EKF and remap all localization nodes' /diagnostics to the namespaced diagnostics topic.
- Rationale: With print_diagnostics false, robot_localization reports a permanent false ERROR ('No events recorded') for the odometry/filtered frequency status; namespacing lets the aggregator group them under Localization.

## SWR-LOC-009: Functional: The rover_localization shall, when fuse_gps (default $ROVER_SYSTEM_USE_GPS) is one of t... (Functional)
The rover_localization shall, when fuse_gps (default $ROVER_SYSTEM_USE_GPS) is one of true/1/yes/on in any case and use_ekf is true, additionally start rover_ekf_global_node, rover_navsat_transform_node and rover_gps_heading_node and load the _with_gps configuration.
- Rationale: Optional absolute positioning for outdoor operation without changing the continuous odom frame.

## SWR-LOC-010: Functional: The rover_localization shall configure rover_ekf_global_node at 50.0 Hz in 2D mode with... (Functional)
The rover_localization shall configure rover_ekf_global_node at 50.0 Hz in 2D mode with world_frame map, fusing the same wheel vx/vy and IMU yaw rate as rover_ekf_node plus X/Y only from odometry/gps, and publish its estimate on odometry/global.
- Rationale: Dual-EKF scheme: GPS corrections appear only in map -> odom, keeping odom continuous for local control.

## SWR-LOC-011: Parameter: The rover_localization shall broadcast map -> odom from rover_ekf_global_node only when... (Functional)
The rover_localization shall broadcast map -> odom from rover_ekf_global_node only when publish_global_tf (default $ROVER_SYSTEM_GPS_MAP_TF) is one of true/1/yes/on, overriding the config's publish_tf.
- Rationale: Only one node may own map -> odom; by default AMCL or SLAM owns it.

## SWR-LOC-012: Interface: The rover_localization shall run rover_navsat_transform_node at 10.0 Hz with a 3.0 s st... (Functional)
The rover_localization shall run rover_navsat_transform_node at 10.0 Hz with a 3.0 s start delay, magnetic_declination_radians 0.0, yaw_offset 0.0 and zero_altitude true, subscribing gps/fix, gps/heading_imu and odometry/global and publishing odometry/gps and gps/filtered, with the datum service at localization/datum.
- Rationale: Converts the GNSS fix into the map frame; the heading already arrives in ENU from rover_gps_heading, so no declination or IMU mounting offset applies.

## SWR-LOC-013: Parameter: The rover_localization shall pass to rover_gps_heading_node publish_heading true, headi... (Functional)
The rover_localization shall pass to rover_gps_heading_node publish_heading true, heading_frame_id <namespace>/base_link, min_heading_std_rad 0.05 and the alignment parameters min_segment_length_m 3.0, min_speed_m_s 0.3, max_yaw_rate_rad_s 0.1, max_yaw_change_rad 0.1, max_horizontal_std_m 5.0, max_fix_gap_s 2.5, max_odometry_age_s 0.5, required_segments 3 and max_offset_std_rad 0.1.
- Rationale: The alignment tuning lives with the localization config that consumes the heading.

## SWR-LOC-014: Parameter: The rover_localization launch file shall accept the arguments use_ekf (default False), ... (Functional)
The rover_localization launch file shall accept the arguments use_ekf (default False), fuse_gps, publish_global_tf, namespace (default $ROVER_SYSTEM_NAMESPACE), localization_mode (rel|enu, default rel), localization_config_path, common_dir_path (default empty), use_sim (default False, sets use_sim_time) and log_level (default INFO).
- Rationale: Single entry point used by rover_bringup and rover_gazebo.

## SWR-LOC-015: Parameter: The rover_localization shall ship a valid configuration file for every value accepted b... (Functional)
The rover_localization shall ship a valid configuration file for every value accepted by the localization_mode argument, including enu.
- Rationale: An accepted launch argument must not lead to a missing-file start failure.

## SWR-LOC-016: Performance: The rover_localization shall have an automated test that verifies the EKF publishes odo... (Functional)
The rover_localization shall have an automated test that verifies the EKF publishes odom at >= 47.5 Hz and the odom -> base_footprint transform from recorded or simulated wheel-odometry and IMU input.
- Rationale: The package currently has no tests, so frame, rate and fusion configuration regressions (SYS-SR-003, SYS-SR-021) go undetected.
