# SWRS_DIAG
rover_diag_manager Software Requirements Specification (ROVER-A1-ROVER_DIAG_MANAGER-SWRS-V-001). rover_diag_manager provides the platform's computer-health monitor (rover_diag_manager_node: CPU usage, CPU temperature, RAM and root-disk usage, published as rover_msgs/SystemStatus and as an 'OS status' diagnostic) and the configuration/launch of the diagnostic_aggregator node that groups every rover node's /diagnostics statuses into the diagnostics_agg tree shown by the Cockpit diagnostics page. It does not itself produce the drive, battery, E-stop or sensor diagnostics; those come from the owning packages and are only grouped here.

## SWR-DIAG-001: Interface: The rover_diag_manager shall publish a rover_msgs/SystemStatus message on the relative ... (Functional)
The rover_diag_manager shall publish a rover_msgs/SystemStatus message on the relative topic system_status (queue depth 10) containing per-core CPU usage, mean CPU load, CPU temperature, RAM usage and disk usage.
- Rationale: Gives the operator UI and logging a numeric view of on-board computer health.

## SWR-DIAG-002: Performance: The rover_diag_manager shall sample the system metrics and publish system_status at the... (Functional)
The rover_diag_manager shall sample the system metrics and publish system_status at the rate set by the publish_frequency parameter, 5.0 Hz in the shipped configuration.
- Rationale: A fixed sampling rate keeps the health view current without loading the CPU.

## SWR-DIAG-003: Parameter: The rover_diag_manager shall declare the parameters cpu_usage_warn_threshold (default 9... (Functional)
The rover_diag_manager shall declare the parameters cpu_usage_warn_threshold (default 95.0 %, bounds 0-100), cpu_temperature_warn_threshold (default 80.0 degC, bounds 0-120), ram_usage_warn_threshold (default 90.0 %, bounds 0-100), disk_usage_warn_threshold (default 90.0 %, bounds 0-100) and publish_frequency (default 5.0 Hz, bounds 0.1-10.0) through generate_parameter_library.
- Rationale: Declared, bounded parameters prevent silent misconfiguration.

## SWR-DIAG-004: Functional: The rover_diag_manager shall re-read the warning thresholds on every sampling tick so t... (Functional)
The rover_diag_manager shall re-read the warning thresholds on every sampling tick so that a threshold changed with `ros2 param set` takes effect at the next tick without restarting the node.
- Rationale: Lets operators tune thresholds on a running rover.

## SWR-DIAG-005: Diagnostics: The rover_diag_manager shall publish an OS status diagnostic (hardware ID Rover PC) on ... (Functional)
The rover_diag_manager shall publish an 'OS status' diagnostic (hardware ID 'Rover PC') on /diagnostics with one key/value per metric (CPU usage, CPU temperature, RAM usage, disk usage) at the diagnostic_updater period.
- Rationale: Brings computer health into the common /diagnostics stream (SYS-SR-022).

## SWR-DIAG-006: Diagnostics: The rover_diag_manager shall grade the OS status diagnostic WARN when any metric is str... (Functional)
The rover_diag_manager shall grade the 'OS status' diagnostic WARN when any metric is strictly above its warning threshold, ERROR when any metric cannot be read, and OK otherwise, using the most severe finding as the overall level.
- Rationale: Makes overload and sensor-read failures of the computer visible to the operator.

## SWR-DIAG-007: Diagnostics: The rover_diag_manager shall report the OS status diagnostic as STALE with the message ... (Functional)
The rover_diag_manager shall report the 'OS status' diagnostic as STALE with the message 'No system sample yet.' until the first metrics sample has been taken.
- Rationale: Avoids reporting OK before any data exists.

## SWR-DIAG-008: Functional: The rover_diag_manager shall read CPU temperature from /sys/class/thermal/thermal_zone0... (Functional)
The rover_diag_manager shall read CPU temperature from /sys/class/thermal/thermal_zone0/temp (millidegrees, converted to degC with 2 decimals), RAM usage as (total - available)/total from /proc/meminfo, and disk usage as (capacity - available)/capacity of the root filesystem '/', and shall report a metric as unknown (NaN on system_status) when it cannot be read or its total is not positive.
- Rationale: Defines what each reported metric means so values can be checked against a reference.

## SWR-DIAG-009: Interface: The rover_diag_manager shall launch a diagnostic_aggregator aggregator_node named rover... (Functional)
The rover_diag_manager shall launch a diagnostic_aggregator aggregator_node named rover_diagnostic_aggregator that subscribes to the namespaced diagnostics topic and publishes diagnostics_agg and diagnostics_toplevel_state inside the launch namespace (ROVER_SYSTEM_NAMESPACE).
- Rationale: The Cockpit diagnostics page consumes diagnostics_agg; relative remaps keep multi-robot namespaces isolated.

## SWR-DIAG-010: Performance: The rover_diag_manager shall configure the diagnostic aggregator to publish diagnostics... (Functional)
The rover_diag_manager shall configure the diagnostic aggregator to publish diagnostics_agg at 1.0 Hz under the root path 'Rover'.
- Rationale: SYS-SR-022 requires diagnostic status at 1 Hz or faster.

## SWR-DIAG-011: Diagnostics: The rover_diag_manager shall group diagnostic statuses by node-name prefix into the agg... (Functional)
The rover_diag_manager shall group diagnostic statuses by node-name prefix into the aggregator paths Computer (rover_diag_manager_node), Drive (rover_hardware_controller, controller_manager), Battery (rover_battery_node), Localization (rover_ekf_node, rover_ekf_global_node, rover_navsat_transform_node), GPS (rover_gps_node, rover_gps_heading_node; only with ROVER_SYSTEM_USE_GPS), Lidar (rover_rs16_lidar_node; only with ROVER_SYSTEM_USE_LIDAR), Lighting (rover_led_driver, rover_led_controller), Teleop (rover_crsf_teleop_node), Motion (rover_motion_lock_node, rover_twist_mux_node) and Safety (rover_safety_node, rover_led_safety_node).
- Rationale: SYS-SR-022 lists drive motors, battery, E-stop circuit and sensors; grouping gives the operator one place per subsystem.

## SWR-DIAG-012: Diagnostics: The rover_diag_manager shall configure the diagnostic aggregator so that the drive, bat... (Functional)
The rover_diag_manager shall configure the diagnostic aggregator so that the drive, battery, E-stop (safety) and sensor (GPS, lidar, IMU) groups report ERROR or STALE when an expected component's diagnostics are missing, rather than silently omitting them.
- Rationale: SYS-SR-022 acceptance requires every listed component to appear at >= 1 Hz; a GenericAnalyzer with only find_and_remove_prefix shows nothing when a node never starts.

## SWR-DIAG-013: Parameter: The rover_diag_manager launch file shall accept the arguments log_level (DEBUG/INFO/WAR... (Functional)
The rover_diag_manager launch file shall accept the arguments log_level (DEBUG/INFO/WARN/ERROR/FATAL, default INFO), namespace (default $ROVER_SYSTEM_NAMESPACE or empty), system_diag_config_path (default config/system_diag.yaml) and diagnostic_aggregator_config_path (default config/diagnostic_aggregator.yaml).
- Rationale: Allows per-deployment override of configuration without rebuilding.

## SWR-DIAG-014: Lifecycle: The rover_diag_manager shall run rover_diag_manager_node as a plain (non-lifecycle) nod... (Functional)
The rover_diag_manager shall run rover_diag_manager_node as a plain (non-lifecycle) node that starts sampling on construction, exits with code 1 and a FATAL log if construction fails (for example on an out-of-range parameter), and stops its timer on context shutdown.
- Rationale: The node owns no hardware resource; fail-fast on bad configuration makes misconfiguration visible.

## SWR-DIAG-015: Build: The rover_diag_manager shall keep its domain and application layers in a separate stati... (Functional)
The rover_diag_manager shall keep its domain and application layers in a separate static library (rover_diag_manager_core) with no ROS or cppuprofile dependency.
- Rationale: Clean Architecture rule: domain has no ROS dependencies; enables fast pure unit tests.
